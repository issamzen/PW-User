'==================================================================
' LifterStudio.CATScript - "CATIA Lifter Parameters" dashboard
'------------------------------------------------------------------
' VBScript edition of the CATVBA macro, executed INSIDE CATIA by the
' PW-User dashboard (SystemService.ExecuteScript). Same HTA user
' interface, same parameter names, same VBA <-> HTA file protocol,
' same PowerCopy hand-off.
'
' CATMain returns to the dashboard:
'   POWERCOPY:<linked>:<drafts>  the user asked for the PowerCopy
'   CLOSED:<linked>:<drafts>     the user closed the dashboard
'   CANCELLED                    first-run setup was cancelled
'   ERROR:<reason>               nothing could be done
'==================================================================

Dim gFso, gShell
Set gFso = CreateObject("Scripting.FileSystemObject")
Set gShell = CreateObject("WScript.Shell")

Const p1 = "UPPER_INTERNAL_LENGTH"
Const p2 = "INTERNAL_VERTICAL_ANGLE"
Const P3 = "INTERNAL_HORIZONTAL_ANGLE"
Const P4 = "HAS_EXTERNAL_FACE"
Const P5 = "UNDERCUT_LENGTH"
Const P_STROKE = "STROKE_Distance"
Const P_DRAFT = "Draft"          ' derived summary angle (per LIFTER_HEAD)
Const DRAFT_MAX_DEG = 15          ' injection molding rule 1: max 15 deg
Const APP_TITLE = "CATIA Lifter Parameters"
Const WAIT_SECONDS = 1800
Const HWND_TOPMOST = -1
Const HWND_NOTOPMOST = -2
Const TOP_FLAGS = 67
Const FAR_DIST = 100000

'==================================================================
' Boolean Remove engine - stored bodies, Paste Special As Result,
' ShapeFactory.AddNewRemove
'==================================================================
' The dashboard picks up two bodies per PowerCopy instance:
'
'   COPY BODY   - the tool body. It is copied, pasted into the
'                 target body "As Result, with out link", renamed
'                 REMOVE_TOOL_I001 and then subtracted.
'   TARGET BODY - the body that receives the Remove feature
'                 (Remove_I001).
'
' Both are chosen by the user with the native CATIA selection prompt
' (SelectElement2), exactly like the MAIN body picker used by the
' first-run setup, and they are kept per instance index so every
' instance can carry its own pair.
'
' Stored CATIA object references are validated against part.bodies
' before every use: a body that has been deleted (or a part that was
' rebuilt) is reported clearly instead of raising a COM error, and
' the dead reference is dropped so the dashboard asks for a new one.
'
' Nothing here is destructive to the ORIGINAL tool body - it stays
' untouched, only the pasted copy is consumed by the Remove.
'==================================================================
Dim gCopyBodyObjects
Dim gTargetBodyObjects
Dim gCopyBodyNames
Dim gTargetBodyNames

Const ERR_BOOLEANSRC_MISSING = 750
Const ERR_BOOLEANNORESLT = 751
Const ERR_BOOLEANFINDRES = 752
Const PASTE_MODE_NOLINK = "CATPrtResultWithOutLink"

'==================================================================
' v2 dashboard - "Lifter Studio" redesign
'------------------------------------------------------------------
' Dark header + instance sidebar (click to select), summary tiles,
' two grouped cards, auto-readout fields (stroke + draft), Enter key
' to apply, dirty-state feedback, live connection dot and a modal
' hand-off screen. Same VBA <-> HTA file protocol as v1, same
' parameter names, same PowerCopy hand-off - drop-in replacement.
'==================================================================

Function CATMain()
    On Error Resume Next

    Dim doc, part
    Dim token, windowTitle
    Dim hta, cmd, rsp
    Dim setupHta, setupCmd, setupRsp
    Dim data, action
    Dim launchPowerCopy
    Dim booleanAction
    Dim linkedCount, draftCount

    launchPowerCopy = False
    CATMain = "ERROR:The lifter dashboard could not start."

    If CATIA.Documents.Count = 0 Then
        MsgBox "Open a CATPart first.", vbExclamation, APP_TITLE
        CATMain = "ERROR:No document is open in CATIA - open the destination CATPart first."
        Exit Function
    End If
    If TypeName(CATIA.ActiveDocument) <> "PartDocument" Then
        MsgBox "The active document must be a CATPart.", vbExclamation, APP_TITLE
        CATMain = "ERROR:The active CATIA document must be a CATPart."
        Exit Function
    End If

    Set doc = CATIA.ActiveDocument
    Set part = doc.Part
    If Err.Number <> 0 Then
        CATMain = "ERROR:The destination CATPart is not accessible."
        Exit Function
    End If

    Randomize
    token = StampText("yyyymmdd_hhnnss") & CStr(Int(Rnd() * 999999))
    windowTitle = APP_TITLE & " - " & token
    hta = TempDir() & "\Lifter_" & token & ".hta"
    cmd = TempDir() & "\LifterCmd_" & token & ".txt"
    rsp = TempDir() & "\LifterRsp_" & token & ".txt"
    setupHta = TempDir() & "\LifterSetup_" & token & ".hta"
    setupCmd = TempDir() & "\LifterSetupCmd_" & token & ".txt"
    setupRsp = TempDir() & "\LifterSetupRsp_" & token & ".txt"
    DeleteFile hta
    DeleteFile cmd
    DeleteFile rsp
    DeleteFile setupHta
    DeleteFile setupCmd
    DeleteFile setupRsp

    ' ===== First run: modern one-time setup =====
    ' When "STROKE_Distance" does not exist yet, the main body is
    ' auto-detected and measured inside a branded setup panel.
    If Not StrokeParameterExists(part) Then
        If Not FirstRunSetup(part, setupHta, setupCmd, setupRsp, windowTitle & " - Setup") Then
            CATMain = "CANCELLED"
            Exit Function
        End If
    End If

    ' ===== Single source of truth for STROKE_Distance =====
    linkedCount = LinkStrokeToMainBody(part)
    draftCount = CreateDraftParameters(part)

    BuildDashboard hta, cmd, rsp, doc.Name, part, windowTitle, linkedCount, draftCount
    ShellRun "mshta.exe " & QuoteText(hta)
    MakeTopmost windowTitle

    Do
        data = WaitCommand(cmd, WAIT_SECONDS)
        If Len(data) = 0 Then Exit Do
        DeleteFile cmd
        DeleteFile rsp          ' never let the dashboard read a stale reply
        action = UCase(ReadKey(data, "COMMAND"))
        If action = "CLOSE" Then Exit Do
        If action = "REFRESH" Then SendValues part, rsp, ReadInstance(data)
        If action = "UPDATE" Then UpdateValues part, data, rsp, ReadInstance(data)
        booleanAction = ""
        If action = "SELECTBODY" Then booleanAction = action
        If action = "REMOVEONE" Then booleanAction = action
        If Len(booleanAction) > 0 Then HandleBooleanCommand part, booleanAction, data, rsp, windowTitle
        If action = "POWERCOPY" Then
            launchPowerCopy = True
            Exit Do
        End If
    Loop

    DeleteFile cmd
    DeleteFile rsp
    If launchPowerCopy Then
        StartPowerCopy
        CATMain = "POWERCOPY:" & CStr(linkedCount) & ":" & CStr(draftCount)
    Else
        DeleteFile hta
        CATMain = "CLOSED:" & CStr(linkedCount) & ":" & CStr(draftCount)
    End If
End Function


'------------------------------------------------------------------
' Returns True when the "STROKE_Distance" parameter already exists,
' False when it is missing. Used to decide whether the MAIN body
' selection must be forced before the dashboard is displayed.
'------------------------------------------------------------------
Function StrokeParameterExists(part)
    On Error Resume Next
    Dim params
    Dim p
    On Error Resume Next
    Set params = part.parameters
    Set p = params.item(P_STROKE)
    Err.Clear
    StrokeParameterExists = Not p Is Nothing
End Function


' ============================================================
' STROKE_Distance "single source of truth"
' ============================================================
' Links each PowerCopy instance's LIFTER_HEAD\STROKE_Distance to the main
' body's root STROKE_Distance. After this, the instance parameter is DRIVEN
' by the root value, so the random placeholder (e.g. 50mm / 100mm) is
' replaced by the real measured STROKE_Distance. Returns the number linked.
' Idempotent: a parameter that is already driven is skipped.
' ============================================================
Function LinkStrokeToMainBody(part)
    On Error Resume Next
    Err.Clear

    Dim rootStroke
    Dim rootName
    Dim relations
    Dim sets, s, strokeP
    Dim i, cnt, errNo

    On Error Resume Next
    Set rootStroke = part.parameters.item(P_STROKE)
    Err.Clear
    If rootStroke Is Nothing Then
        LinkStrokeToMainBody = 0
        Exit Function
    End If

    On Error Resume Next
    rootName = part.parameters.GetNameToUseInRelation(rootStroke)
    Err.Clear
    If Len(Trim(rootName)) = 0 Then
        LinkStrokeToMainBody = 0
        Exit Function
    End If

    Set relations = part.Relations
    Set sets = GetHeadSets(part)
    cnt = 0

    For i = 1 To sets.Count
        Set s = sets.Item(i)
        Set strokeP = Nothing
        Err.Clear
        Set strokeP = s.DirectParameters.Item(P_STROKE)
        Err.Clear
        If Not strokeP Is Nothing Then
            Err.Clear
            relations.CreateFormula "", "", strokeP, rootName
            errNo = Err.Number
            Err.Clear
            If errNo = 0 Then cnt = cnt + 1
        End If
    Next

    part.Update
    Err.Clear
    LinkStrokeToMainBody = cnt
End Function


' ============================================================
' Draft parameter (injection-molding rules)
' ============================================================
' For each LIFTER_HEAD set that contains UNDERCUT_LENGTH and
' STROKE_Distance, creates/refreshes an Angle parameter named "Draft":
'
'   Draft = min( floor( atan( ( UNDERCUT_LENGTH + 5mm ) / STROKE_Distance ) * 180/PI + 0.5 ), 15 ) * 1deg
'
' Rule 1: capped at 15 deg (min).
' Rule 2: rounded to the nearest whole degree, half rounds UP (floor(x+0.5)),
'         so 8.5 -> 9 and 8.9 -> 9.
' Rule 3: 5 mm is added to UNDERCUT_LENGTH before the atan.
' Any existing formula on the Draft parameter is REPLACED so the current
' rule always takes effect. Returns the number of Draft formulas created.
' ============================================================
Function CreateDraftParameters(part)
    On Error Resume Next

    Dim relations
    Dim sets, s
    Dim undercutP, strokeP, draftP
    Dim undercutName, strokeName, formulaText
    Dim i, cnt, errNo
    Dim oldRel

    Set relations = part.Relations
    Set sets = GetHeadSets(part)
    cnt = 0

    For i = 1 To sets.Count
        Set s = sets.Item(i)

        Set undercutP = Nothing
        Set strokeP = Nothing
        Set draftP = Nothing
        Err.Clear
        Set undercutP = s.DirectParameters.Item(P5)
        Set strokeP = s.DirectParameters.Item(P_STROKE)
        Err.Clear

        If (Not undercutP Is Nothing) And (Not strokeP Is Nothing) Then

            ' Get or create the Draft Angle parameter inside this LIFTER_HEAD set.
            Set draftP = s.DirectParameters.Item(P_DRAFT)
            Err.Clear
            If draftP Is Nothing Then
                Set draftP = s.DirectParameters.CreateDimension(P_DRAFT, "ANGLE", 0)
                Err.Clear
            End If

            If Not draftP Is Nothing Then
                ' Robust paths to the two inputs.
                undercutName = part.Parameters.GetNameToUseInRelation(undercutP)
                strokeName = part.Parameters.GetNameToUseInRelation(strokeP)
                Err.Clear

                formulaText = "min( floor( atan( ( " & undercutName & " + 5mm ) / " & strokeName _
                              & " ) * 180 / PI + 0.5 ), " & CStr(DRAFT_MAX_DEG) & " ) * 1deg"

                ' Replace any existing formula driving this Draft parameter so the
                ' current rule (with +5mm) always wins over an older formula.
                Set oldRel = GetFormulaFor(relations, draftP)
                If Not oldRel Is Nothing Then
                    relations.Remove oldRel.Name
                    Err.Clear
                End If

                ' Create the formula (idempotent in effect: one formula per parameter).
                Err.Clear
                relations.CreateFormula "", "", draftP, formulaText
                errNo = Err.Number
                Err.Clear
                If errNo = 0 Then cnt = cnt + 1
            End If
        End If
    Next

    part.Update
    Err.Clear
    CreateDraftParameters = cnt
End Function


'------------------------------------------------------------------
' Returns the formula relation currently driving a parameter, or
' Nothing. TypeName/LeftPart are probed defensively so this works
' across CATIA releases.
'------------------------------------------------------------------
Function GetFormulaFor(relations, drivenParameter)
    On Error Resume Next
    Dim i, rel, leftName, wantedName
    Set GetFormulaFor = Nothing
    If relations Is Nothing Or drivenParameter Is Nothing Then Exit Function

    wantedName = CStr(drivenParameter.Name)
    For i = 1 To relations.Count
        Set rel = Nothing
        Set rel = relations.Item(i)
        If Not rel Is Nothing Then
            If TypeName(rel) = "Formula" Then
                If rel.LeftPart Is drivenParameter Then
                    Set GetFormulaFor = rel
                    Err.Clear
                    Exit Function
                End If
                ' CATIA hands out a fresh proxy for the same parameter, so
                ' the driven name is compared as well.
                leftName = ""
                leftName = CStr(rel.LeftPart.Name)
                Err.Clear
                If Len(leftName) > 0 Then
                    If StrComp(leftName, wantedName, vbTextCompare) = 0 Then
                        Set GetFormulaFor = rel
                        Err.Clear
                        Exit Function
                    End If
                End If
            End If
        End If
    Next
    Err.Clear
End Function


' ============================================================
' Standalone entry point
' ============================================================
' Use this instead of the full dashboard when you only want to
' (re)link STROKE_Distance and (re)create Draft after instantiating.
' ============================================================
Sub LinkStrokeAndCreateDraft()
    On Error Resume Next
    Err.Clear

    If CATIA.Documents.count = 0 Then
        MsgBox "Open a CATPart first.", vbExclamation, APP_TITLE
        Exit Sub
    End If
    If TypeName(CATIA.ActiveDocument) <> "PartDocument" Then
        MsgBox "The active document must be a CATPart.", vbExclamation, APP_TITLE
        Exit Sub
    End If

    Dim part
    Set part = CATIA.ActiveDocument.part

    If Not StrokeParameterExists(part) Then
        ' Same modern first-run setup as the full dashboard entry point.
        Dim setupToken, setupHta, setupCmd, setupRsp
        Randomize
        setupToken = StampText("yyyymmdd_hhnnss") & CStr(Int(Rnd() * 999999))
        setupHta = TempDir() & "\LifterSetup_" & setupToken & ".hta"
        setupCmd = TempDir() & "\LifterSetupCmd_" & setupToken & ".txt"
        setupRsp = TempDir() & "\LifterSetupRsp_" & setupToken & ".txt"
        DeleteFile setupHta
        DeleteFile setupCmd
        DeleteFile setupRsp
        If Not FirstRunSetup(part, setupHta, setupCmd, setupRsp, APP_TITLE & " - Setup") Then
            Exit Sub        ' cancelled by the user
        End If
    End If

    Dim linked, drafts
    linked = LinkStrokeToMainBody(part)
    drafts = CreateDraftParameters(part)

    If Err.Number <> 0 Then
        MsgBox "Fix-up stopped." & vbCrLf & Err.Description, vbCritical, APP_TITLE
        Err.Clear
        Exit Sub
    End If

    MsgBox "Linked " & linked & " instance STROKE_Distance parameter(s) to the main body." & vbCrLf & _
           "Created/refreshed " & drafts & " Draft parameter(s).", vbInformation, APP_TITLE
End Sub


'==================================================================
' STROKE = W of the STANDARD bounding box (XYZ axes).
'==================================================================
Function CalculateSTROKEDistance(part)
    On Error Resume Next
    Err.Clear

    Dim sel
    Dim mainBody

    Set sel = part.Parent.Selection

    '----- Select body (manual fallback only - the setup panel uses
    '      MeasureStrokeOnBody with an auto-detected body) -----
    sel.Clear
    If sel.SelectElement2(Array("Body"), "Select the MAIN body for STROKE_Distance...", False) <> "Normal" Then
        CalculateSTROKEDistance = False
        Exit Function
    End If
    Set mainBody = sel.item(1).value
    sel.Clear

    If Err.Number <> 0 Then
        Err.Clear
        CalculateSTROKEDistance = False
        Exit Function
    End If

    CalculateSTROKEDistance = MeasureStrokeOnBody(part, mainBody)
End Function


'------------------------------------------------------------------
' Measures STROKE_Distance from the given body: W of the STANDARD
' bounding box (XYZ axes), same BBox-macro logic as before. Creates
' or updates the STROKE_Distance parameter, then removes the
' TEMP_STROKE geometrical set. Returns False when it fails.
'------------------------------------------------------------------
Function MeasureStrokeOnBody(part, mainBody)
    On Error Resume Next

    Dim hsf, spaWB, gs, refBody
    Dim lineX, lineY, lineZ
    Dim extWmax, extWmin, planeWmax, planeWmin
    Dim m, W, params, p

    MeasureStrokeOnBody = False

    Set hsf = part.HybridShapeFactory
    Set spaWB = part.Parent.GetWorkbench("SPAWorkbench")
    If Err.Number <> 0 Then
        Err.Clear
        Exit Function
    End If

    '----- Temporary set (deleted at start AND at the end) -----
    DeleteGeometricalSet part, "TEMP_STROKE"
    Err.Clear
    Set gs = part.HybridBodies.Add
    gs.Name = "TEMP_STROKE"

    Set refBody = part.CreateReferenceFromObject(mainBody)
    If Err.Number <> 0 Then
        Err.Clear
        DeleteGeometricalSet part, "TEMP_STROKE"
        Exit Function
    End If

    '----- STANDARD box axes (choice "1" of the BBox macro) -----
    Set lineX = hsf.AddNewLinePtPt(hsf.AddNewPointCoord(-10000, 0, 0), hsf.AddNewPointCoord(10000, 0, 0))
    Set lineY = hsf.AddNewLinePtPt(hsf.AddNewPointCoord(0, -10000, 0), hsf.AddNewPointCoord(0, 10000, 0))
    Set lineZ = hsf.AddNewLinePtPt(hsf.AddNewPointCoord(0, 0, -10000), hsf.AddNewPointCoord(0, 0, 10000))
    gs.AppendHybridShape lineX
    gs.AppendHybridShape lineY
    gs.AppendHybridShape lineZ

    '----- The 2 extremums of W (direction Y), BBox-macro style -----
    Set extWmax = Build_BoxExtremum(hsf, refBody, 1, lineY, lineZ, lineX)   ' max along Y
    Set extWmin = Build_BoxExtremum(hsf, refBody, 0, lineY, lineZ, lineX)   ' min along Y
    gs.AppendHybridShape extWmax
    gs.AppendHybridShape extWmin

    '----- The 2 limit planes of W -----
    Set planeWmax = hsf.AddNewPlaneNormal(lineY, extWmax)
    Set planeWmin = hsf.AddNewPlaneNormal(lineY, extWmin)
    gs.AppendHybridShape planeWmax
    gs.AppendHybridShape planeWmin
    part.Update

    If Err.Number <> 0 Then
        Err.Clear
        DeleteGeometricalSet part, "TEMP_STROKE"
        Exit Function
    End If

    '----- W = distance between the 2 planes (standard measure) -----
    Set m = spaWB.GetMeasurable(planeWmax)
    W = m.GetMinimumDistance(planeWmin)
    If Err.Number <> 0 Or Not IsNumeric(W) Then
        Err.Clear
        DeleteGeometricalSet part, "TEMP_STROKE"
        Exit Function
    End If

    '----- Keep ONLY W: parameter -----
    Set params = part.Parameters
    Set p = Nothing
    Err.Clear
    Set p = params.Item(P_STROKE)
    Err.Clear
    If p Is Nothing Then
        Set p = params.CreateDimension(P_STROKE, "LENGTH", W)
    Else
        p.Value = W
    End If
    If Err.Number <> 0 Then
        Err.Clear
        DeleteGeometricalSet part, "TEMP_STROKE"
        Exit Function
    End If

    '----- Remove the TEMP_STROKE geometrical set entirely -----
    DeleteGeometricalSet part, "TEMP_STROKE"
    part.Update
    Err.Clear

    MeasureStrokeOnBody = True
End Function


'------------------------------------------------------------------
' Auto-detects the main body: part.MainBody first, then the first
' body of the Bodies collection. Returns Nothing when no body exists.
'------------------------------------------------------------------
Function DetectMainBody(part)
    On Error Resume Next
    Dim bodies, found
    Set found = Nothing
    Set found = part.MainBody
    Err.Clear
    If found Is Nothing Then
        Set bodies = Nothing
        Set bodies = part.Bodies
        Err.Clear
        If Not bodies Is Nothing Then
            If bodies.Count > 0 Then Set found = bodies.Item(1)
        End If
        Err.Clear
    End If
    Set DetectMainBody = found
End Function


'------------------------------------------------------------------
' Returns the current STROKE_Distance value as plain text ("" when
' the parameter does not exist).
'------------------------------------------------------------------
Function strokeText(part)
    On Error Resume Next
    Dim p
    On Error Resume Next
    Set p = part.parameters.item(P_STROKE)
    If Not p Is Nothing Then strokeText = ValueOnly(p)
    Err.Clear
End Function


'------------------------------------------------------------------
' Writes the setup result file read by the setup panel:
'   RESULT=OK|FAIL
'   VALUE=42.5
'------------------------------------------------------------------
Sub SetupResponse(path, result, value)
    On Error Resume Next
    Dim f
    DeleteFile path
    Set f = NewWriter(path)
    If f Is Nothing Then Exit Sub
    f.WriteLine "RESULT=" & result
    f.WriteLine "VALUE=" & value
    f.Close
    Err.Clear
End Sub


'==================================================================
' First run setup - modern, automated STROKE_Distance measurement
'==================================================================
' STROKE_Distance is missing, so the main body is auto-detected
' (part.MainBody, fallback: first body) and measured while a branded
' setup panel shows live progress:
'   detect -> measure -> show result -> Continue / Cancel
'   on failure -> Retry / Choose another body (native CATIA prompt)
' Returns False when the user cancels.
'==================================================================
Function FirstRunSetup(part, hta, cmd, rsp, setupTitle)
    On Error Resume Next

    Dim foundBody, detectText, detectOk
    Dim data, action

    ' 1) Auto-detect the main body - no prompt in the normal case
    Set foundBody = DetectMainBody(part)
    If foundBody Is Nothing Then
        detectText = "No main body found - use 'Choose another body'."
        detectOk = False
    Else
        detectText = "Main body detected - " & CStr(foundBody.name)
        detectOk = True
    End If

    ' 2) Launch the branded setup panel first so the user sees activity
    BuildSetupHta hta, cmd, rsp, setupTitle, detectText, detectOk
    ShellRun "mshta.exe " & QuoteText(hta)
    MakeTopmost setupTitle

    ' 3) Measure with the detected body and report back to the panel
    If foundBody Is Nothing Then
        SetupResponse rsp, "FAIL", ""
    Else
        If MeasureStrokeOnBody(part, foundBody) Then
            SetupResponse rsp, "OK", strokeText(part)
        Else
            SetupResponse rsp, "FAIL", ""
        End If
    End If

    ' 4) Wait for the user's decision
    Do
        data = WaitCommand(cmd, WAIT_SECONDS)
        If Len(data) = 0 Then Exit Do
        DeleteFile cmd
        action = UCase(ReadKey(data, "COMMAND"))
        If action = "CONTINUE" Then
            FirstRunSetup = True
            Exit Do
        End If
        If action = "CANCEL" Then
            FirstRunSetup = False
            Exit Do
        End If
        If action = "MANUAL" Then
            ' fallback: let the user pick the body in CATIA
            DeleteFile rsp
            If CalculateSTROKEDistance(part) Then
                SetupResponse rsp, "OK", strokeText(part)
            Else
                SetupResponse rsp, "FAIL", ""
            End If
        End If
        If action = "RETRY" Then
            DeleteFile rsp
            If Not foundBody Is Nothing Then
                If MeasureStrokeOnBody(part, foundBody) Then
                    SetupResponse rsp, "OK", strokeText(part)
                Else
                    SetupResponse rsp, "FAIL", ""
                End If
            Else
                SetupResponse rsp, "FAIL", ""
            End If
        End If
    Loop

    ' Errors are never fatal here: the setup panel already shows the
    ' FAIL state and offers Retry / Choose another body / Cancel.
    Err.Clear

    DeleteFile cmd
    DeleteFile rsp
    DeleteFile hta
    Err.Clear
End Function


'==================================================================
' Setup panel (HTA) - branded first-run experience
'==================================================================
Sub BuildSetupHta(hta, cmd, rsp, title, detectText, detectOk)
    On Error Resume Next
    Dim f
    Set f = NewWriter(hta)
    If f Is Nothing Then Exit Sub
    W f, "<html><head><title>" & H(title) & "</title>"
    W f, "<HTA:APPLICATION BORDER='thin' CAPTION='yes' SCROLL='no' SINGLEINSTANCE='yes'>"
    W f, "<meta http-equiv='X-UA-Compatible' content='IE=9'>"
    WriteSetupCss f
    WriteSetupJs f, cmd, rsp
    W f, "</head><body onload='init()' onbeforeunload='closing()'>"

    W f, "<div class='top'>"
    W f, "<div class='logo'>L</div>"
    W f, "<div class='brand'><div class='bt'>Lifter Studio</div><div class='bs'>One-time setup</div></div>"
    W f, "<div class='conn'><span class='dot' id='topDot'></span><span id='topText'>Setup</span></div>"
    W f, "</div>"

    W f, "<div class='page'><div class='card'>"
    W f, "<div class='kicker'>FIRST RUN</div>"
    W f, "<div class='title'>STROKE_Distance not found</div>"
    W f, "<div class='body'>This value is measured once from the main body's bounding box width and becomes the single source of truth for every lifter instance.</div>"

    If detectOk Then
        W f, "<div class='detect'><span class='dot ok'></span>" & H(detectText) & "</div>"
    Else
        W f, "<div class='detect'><span class='dot err'></span>" & H(detectText) & "</div>"
    End If

    W f, "<div class='progressWrap' id='progressWrap'>"
    W f, "<div class='progLabel' id='progLabel'>Measuring bounding box width...</div>"
    W f, "<div class='progress'><div class='bar' id='bar'></div></div>"
    W f, "</div>"

    W f, "<div class='result' id='resultOk' style='display:none'>"
    W f, "<div class='big'><span id='vNum'>-</span> <span class='u'>mm</span></div>"
    W f, "<div class='okText'>STROKE_Distance created - the dashboard opens next.</div>"
    W f, "</div>"

    W f, "<div class='result err' id='resultFail' style='display:none'>"
    W f, "<div class='errText'>Measurement failed.</div>"
    W f, "<div class='errSub'>The body could not be measured - retry, pick another body, or continue without STROKE_Distance.</div>"
    W f, "</div>"

    W f, "<div class='actions'>"
    W f, "<button id='btnCancel' onclick='goCancel()'>Cancel</button>"
    W f, "<button id='btnManual' onclick='goManual()'>Choose another body</button>"
    W f, "<button id='btnRetry' onclick='goRetry()' style='display:none'>Retry</button>"
    W f, "<button id='btnGo' class='apply dim' onclick='goContinue()' disabled>Continue</button>"
    W f, "</div>"

    W f, "<div class='foot'>Setup runs only once - the next launch opens the dashboard directly.</div>"
    W f, "</div></div>"

    W f, "</body></html>"
    f.Close
End Sub


'------------------------------------------------------------------
' Setup panel CSS (same visual language as the dashboard)
'------------------------------------------------------------------
Sub WriteSetupCss(f)
    On Error Resume Next
    W f, "<style>"
    W f, "html,body{margin:0;font-family:'Segoe UI',Arial,sans-serif;background:#edf1f5;color:#1d2d3c;font-size:12px}"
    W f, "body{overflow:hidden}"
    W f, ".top{position:relative;height:56px;background:#10222e}"
    W f, ".logo{position:absolute;left:18px;top:11px;width:34px;height:34px;line-height:34px;text-align:center;background:#16a7b4;color:#fff;border-radius:9px;font-size:16px;font-weight:700}"
    W f, ".brand{position:absolute;left:64px;top:10px}.bt{color:#fff;font-size:15px;font-weight:600}.bs{color:#7e96a5;font-size:10px;margin-top:1px}"
    W f, ".conn{position:absolute;right:18px;top:20px;color:#a5d6de;font-size:10px}"
    W f, ".dot{display:inline-block;width:8px;height:8px;border-radius:50%;background:#f0b64b;vertical-align:middle;margin-right:6px}"
    W f, ".dot.ok{background:#43c46b}.dot.err{background:#e4574f}"
    W f, ".page{padding:18px 20px}"
    W f, ".card{background:#fff;border:1px solid #dfe6ed;border-radius:12px;box-shadow:0 4px 14px rgba(16,34,46,.06);padding:18px 18px 10px}"
    W f, ".kicker{font-size:9px;font-weight:700;letter-spacing:2px;color:#0f8891;margin-bottom:6px}"
    W f, ".title{font-size:17px;font-weight:700;color:#10222e}"
    W f, ".body{font-size:11px;color:#7b8a9b;margin:8px 0 14px;line-height:16px}"
    W f, ".detect{font-size:11px;color:#44586b;background:#f1fafb;border:1px solid #cfe8ec;border-radius:8px;padding:8px 10px;margin-bottom:14px}"
    W f, ".progressWrap{margin-bottom:14px}"
    W f, ".progLabel{font-size:10px;color:#7b8a9b;margin-bottom:6px}"
    W f, ".progress{height:8px;background:#e4ecf2;border-radius:4px;overflow:hidden}"
    W f, ".bar{height:8px;width:0;background:#16a7b4;border-radius:4px}"
    W f, ".result{margin-bottom:14px;padding:14px;border-radius:10px;background:#f2fbf4;border:1px solid #c9e9d0}"
    W f, ".result.err{background:#fdf3f2;border:1px solid #efcfcc}"
    W f, ".big{font-size:26px;font-weight:700;color:#10222e}.u{font-size:12px;color:#7b8a9b;font-weight:600}"
    W f, ".okText{font-size:10px;color:#2e7d4f;margin-top:4px}"
    W f, ".errText{font-size:13px;font-weight:700;color:#b03a30}.errSub{font-size:10px;color:#9a6a66;margin-top:4px}"
    W f, ".actions{text-align:right;padding:2px 0 6px}"
    W f, "button{border:1px solid #dfe6ed;border-radius:8px;padding:9px 14px;margin-left:6px;font-size:11px;font-weight:600;cursor:pointer;background:#fff;color:#44586b;font-family:'Segoe UI',Arial,sans-serif}"
    W f, "button:hover{border-color:#b9cbd6;background:#f6f9fb}"
    W f, "button.apply{background:#0f8891;border-color:#0f8891;color:#fff}"
    W f, "button.apply:hover{background:#0c7078}"
    W f, "button.dim{opacity:.45}"
    W f, ".foot{font-size:9px;color:#9aa8b6;margin-top:10px}"
    W f, "</style>"
End Sub


'------------------------------------------------------------------
' Setup panel JS (IE9-safe)
'------------------------------------------------------------------
Sub WriteSetupJs(f, cmd, rsp)
    On Error Resume Next
    W f, "<script language='javascript'>"
    W f, "var cp='" & JS(cmd) & "';var rp='" & JS(rsp) & "';var handled=false;var done=false;var anim=null;"
    W f, "function $(i){return document.getElementById(i)}"
    W f, "function fs(){return new ActiveXObject('Scripting.FileSystemObject')}"
    W f, "function init(){var w=560,h=470;window.resizeTo(w,h);window.moveTo(Math.round((screen.availWidth-w)/2),Math.round((screen.availHeight-h)/2));setAnim();setInterval(check,300)}"
    W f, "function setAnim(){if(anim)return;var p=0;anim=setInterval(function(){p=(p+6)%100;$('bar').style.width=p+'%'},70)}"
    W f, "function stopAnim(full){if(anim){clearInterval(anim);anim=null}$('bar').style.width=full?'100%':'0'}"
    W f, "function sendCmd(t){try{var x=fs();if(x.FileExists(cp))return false;var f2=x.CreateTextFile(cp,true,false);f2.Write(t);f2.Close();return true}catch(e){return false}}"
    W f, "function check(){try{var x=fs();if(!x.FileExists(rp))return;var f2=x.OpenTextFile(rp,1);var t=f2.ReadAll();f2.Close();readRsp(t)}catch(e){}}"
    W f, "function readRsp(t){var o={};var a=t.split(/\r?\n/);for(var i=0;i<a.length;i++){var p=a[i].indexOf('=');if(p>0)o[a[i].substring(0,p)]=a[i].substring(p+1)}"
    W f, "if(o.RESULT=='OK'){done=true;stopAnim(true);$('progressWrap').style.display='none';$('resultOk').style.display='block';$('resultFail').style.display='none';$('vNum').innerText=o.VALUE;$('topDot').className='dot ok';$('topText').innerText='Done';$('btnGo').disabled=false;$('btnGo').className='apply';$('btnRetry').style.display='none'}"
    W f, "if(o.RESULT=='FAIL'){done=true;stopAnim(false);$('progressWrap').style.display='none';$('resultOk').style.display='none';$('resultFail').style.display='block';$('topDot').className='dot err';$('topText').innerText='Failed';$('btnRetry').style.display='inline-block';$('btnGo').disabled=false;$('btnGo').className='apply'}}"
    W f, "function resetUi(){$('resultOk').style.display='none';$('resultFail').style.display='none';$('progressWrap').style.display='block';$('progLabel').innerText='Measuring bounding box width...';$('topDot').className='dot';$('topText').innerText='Working';$('btnGo').disabled=true;$('btnGo').className='apply dim';$('btnRetry').style.display='none';setAnim()}"
    W f, "function goContinue(){handled=true;sendCmd('COMMAND=CONTINUE\r\n');window.close()}"
    W f, "function goCancel(){handled=true;sendCmd('COMMAND=CANCEL\r\n');window.close()}"
    W f, "function goManual(){resetUi();sendCmd('COMMAND=MANUAL\r\n')}"
    W f, "function goRetry(){resetUi();sendCmd('COMMAND=RETRY\r\n')}"
    W f, "function closing(){if(!handled)sendCmd('COMMAND=CANCEL\r\n')}"
    W f, "</script>"
End Sub

'------------------------------------------------------------------
' Extremum with 3 locked directions - Build_Extremums of the BBox
' macro, same logic: minMax along dir1, locked by dir2 and dir3.
' ALWAYS returns a point, even when the body top is flat.
' minMax: 1 = max, 0 = min.
'------------------------------------------------------------------
Function Build_BoxExtremum(hsf, refBody, _
                                   minMax, _
                                   dir1, dir2, dir3)
    On Error Resume Next
    Dim d1, d2, d3
    Dim ext

    Set d1 = hsf.AddNewDirection(dir1)
    Set d2 = hsf.AddNewDirection(dir2)
    Set d3 = hsf.AddNewDirection(dir3)

    Set ext = hsf.AddNewExtremum(refBody, d1, minMax)
    ext.Direction2 = d2
    ext.ExtremumType2 = 1
    ext.Direction3 = d3
    ext.ExtremumType3 = 1
    ext.Compute

    Set Build_BoxExtremum = ext
End Function


'------------------------------------------------------------------
' Deletes the geometrical set by name. Uses the exact same
' name-based access + Selection.Delete as the recorded macro.
' Repeats until no set with that name remains.
'------------------------------------------------------------------
Sub DeleteGeometricalSet(part, gsName)
    On Error Resume Next
    Dim sel
    Dim hb

    Set sel = part.Parent.Selection

    Do
        Set hb = Nothing
        On Error Resume Next
        Set hb = part.HybridBodies.item(gsName)   ' BY NAME - like the recorder
        Err.Clear
        If hb Is Nothing Then Exit Do

        sel.Clear
        sel.Add hb                                ' add the set to the selection
        sel.Delete                                ' delete it (proven method)
        sel.Clear
    Loop

    part.Update
End Sub


Function GetOrCreateHybridBody(coll, nm)
    On Error Resume Next
    Dim hb
    On Error Resume Next
    Set hb = coll.item(nm)
    Err.Clear
    If hb Is Nothing Then
        Set hb = coll.Add
        hb.name = nm
    End If
    Set GetOrCreateHybridBody = hb
End Function

Sub DeleteAllInGS(part, gs)
    On Error Resume Next
    Dim i
    For i = gs.HybridShapes.count To 1 Step -1
        On Error Resume Next
        part.HybridShapeFactory.DeleteObjectForObject gs.HybridShapes.item(i)
        Err.Clear
    Next
End Sub


' ============================================================
' Boolean Remove - body storage
' ============================================================
' Four parallel collections keyed by the instance index rendered as
' "001" / "002" / ... The two object collections hold the live CATIA
' references, the two text collections hold the names that were shown
' to the user when the body was stored (the body may have been
' renamed afterwards, and the name must survive a failed update).
' ============================================================
Sub EnsureBodyCollections()
    On Error Resume Next
    If Not IsObject(gCopyBodyObjects) Then Set gCopyBodyObjects = NewStore()
    If Not IsObject(gTargetBodyObjects) Then Set gTargetBodyObjects = NewStore()
    If Not IsObject(gCopyBodyNames) Then Set gCopyBodyNames = NewStore()
    If Not IsObject(gTargetBodyNames) Then Set gTargetBodyNames = NewStore()
    If gCopyBodyObjects Is Nothing Then Set gCopyBodyObjects = NewStore()
    If gTargetBodyObjects Is Nothing Then Set gTargetBodyObjects = NewStore()
    If gCopyBodyNames Is Nothing Then Set gCopyBodyNames = NewStore()
    If gTargetBodyNames Is Nothing Then Set gTargetBodyNames = NewStore()
    Err.Clear
End Sub

Function NewStore()
    Set NewStore = CreateObject("Scripting.Dictionary")
End Function

Function StoredKey(instanceIndex)
    StoredKey = Pad3(instanceIndex)
End Function

Function InstanceTag(instanceIndex)
    InstanceTag = Pad3(instanceIndex)
End Function

'------------------------------------------------------------------
' The stores keep body NAMES, not COM references: the application
' calls this script once per dashboard command, so nothing survives
' in memory between two commands. A name is resolved to the live
' body on every use.
'------------------------------------------------------------------
Function GetStoredObject(store, instanceIndex)
    On Error Resume Next
    Set GetStoredObject = Nothing
    If store Is Nothing Then Exit Function
    Dim nm
    nm = GetStoredText(store, instanceIndex)
    If Len(nm) = 0 Then Exit Function
    Set GetStoredObject = ResolveBodyByName(nm)
    Err.Clear
End Function

Sub SetStoredObject(store, instanceIndex, item)
    On Error Resume Next
    Dim nm
    nm = ""
    If Not item Is Nothing Then nm = CStr(item.Name)
    SetStoredText store, instanceIndex, nm
    Err.Clear
End Sub

Function ResolveBodyByName(nm)
    On Error Resume Next
    Set ResolveBodyByName = Nothing
    If gPart Is Nothing Then Exit Function
    Set ResolveBodyByName = gPart.Bodies.Item(nm)
    Err.Clear
End Function

Function GetStoredText(store, instanceIndex)
    On Error Resume Next
    GetStoredText = ""
    If store Is Nothing Then Exit Function
    If store.Exists(StoredKey(instanceIndex)) Then GetStoredText = CStr(store.Item(StoredKey(instanceIndex)))
    Err.Clear
End Function

Sub SetStoredText(store, instanceIndex, text)
    On Error Resume Next
    If store Is Nothing Then Exit Sub
    If store.Exists(StoredKey(instanceIndex)) Then store.Remove StoredKey(instanceIndex)
    store.Add StoredKey(instanceIndex), text
    Err.Clear
End Sub

'------------------------------------------------------------------
' Drops the stored reference AND the displayed name for one instance,
' so the dashboard slot goes back to "not selected".
'------------------------------------------------------------------
Sub ClearStoredBody(objects, names, instanceIndex)
    On Error Resume Next
    If Not objects Is Nothing Then
        If objects.Exists(StoredKey(instanceIndex)) Then objects.Remove StoredKey(instanceIndex)
    End If
    If Not names Is Nothing Then
        If names.Exists(StoredKey(instanceIndex)) Then names.Remove StoredKey(instanceIndex)
    End If
    Err.Clear
End Sub
Function StoredInstanceName(part, isCopyBody, instanceIndex)
    On Error Resume Next
    EnsureBodyCollections
    StoredInstanceName = ""
    If isCopyBody Then
        If GetStoredObject(gCopyBodyObjects, instanceIndex) Is Nothing Then Exit Function
        If Not IsBodyObjectUsable(part, GetStoredObject(gCopyBodyObjects, instanceIndex)) Then Exit Function
        StoredInstanceName = GetStoredText(gCopyBodyNames, instanceIndex)
    Else
        If GetStoredObject(gTargetBodyObjects, instanceIndex) Is Nothing Then Exit Function
        If Not IsBodyObjectUsable(part, GetStoredObject(gTargetBodyObjects, instanceIndex)) Then Exit Function
        StoredInstanceName = GetStoredText(gTargetBodyNames, instanceIndex)
    End If
End Function


' ============================================================
' Boolean Remove - validation helpers
' ============================================================

'------------------------------------------------------------------
' True when the stored reference still points at a body that lives
' in this part's Bodies collection. Reading .Name catches the
' "object no longer valid" COM error, the collection walk catches a
' reference that survived a rebuild but belongs to another body.
'------------------------------------------------------------------
Function IsBodyObjectUsable(part, bodyObject)
    On Error Resume Next
    Dim bodies
    Dim probeName
    Dim i

    IsBodyObjectUsable = False
    If bodyObject Is Nothing Then Exit Function

    On Error Resume Next
    probeName = CStr(bodyObject.name)
    If Err.Number <> 0 Then
        Err.Clear
        Err.Clear
        Exit Function
    End If
    Err.Clear

    On Error Resume Next
    Set bodies = part.bodies
    Err.Clear
    If bodies Is Nothing Then Exit Function

    On Error Resume Next
    For i = 1 To bodies.count
        If bodies.item(i) Is bodyObject Then
            IsBodyObjectUsable = True
            Exit Function
        End If
    Next
    Err.Clear
End Function

'------------------------------------------------------------------
' Identity test for two CATIA references. CATIA hands out a fresh
' COM proxy for the same underlying object, so "Is" alone is not
' enough. Resolve each reference to its index in part.bodies (by
' proxy first, by unique name as fallback) and compare the indexes -
' two different bodies always land on different indexes.
'------------------------------------------------------------------
Function AreSameCATIAObject(part, first, second)
    On Error Resume Next
    Dim bodies
    Dim i
    Dim firstIndex, secondIndex

    AreSameCATIAObject = False
    If first Is Nothing Or second Is Nothing Then Exit Function
    If first Is second Then
        AreSameCATIAObject = True
        Exit Function
    End If

    On Error Resume Next
    Set bodies = part.bodies
    Err.Clear
    If bodies Is Nothing Then Exit Function

    firstIndex = 0
    secondIndex = 0
    On Error Resume Next
    For i = 1 To bodies.count
        If firstIndex = 0 Then
            If bodies.item(i) Is first Then firstIndex = i
            If StrComp(CStr(bodies.item(i).name), CStr(first.name), vbTextCompare) = 0 Then firstIndex = i
        End If
        If secondIndex = 0 Then
            If bodies.item(i) Is second Then secondIndex = i
            If StrComp(CStr(bodies.item(i).name), CStr(second.name), vbTextCompare) = 0 Then secondIndex = i
        End If
    Next
    Err.Clear

    If firstIndex > 0 And secondIndex > 0 Then
        AreSameCATIAObject = (firstIndex = secondIndex)
    End If
End Function


' ============================================================
' Boolean Remove - naming
' ============================================================

'------------------------------------------------------------------
' First free REMOVE_TOOL_I001 / _2 / _3 ... name in the part, so a
' body that was renamed by hand never gets clobbered.
'------------------------------------------------------------------
Function GetUniqueBodyName(bodies, baseName)
    On Error Resume Next
    Dim candidate
    Dim suffix
    Dim taken
    Dim probe

    candidate = baseName
    suffix = 1
    Do
        taken = False
        Set probe = Nothing
        On Error Resume Next
        Err.Clear
        Set probe = bodies.item(candidate)
        If Err.Number = 0 And Not probe Is Nothing Then taken = True
        Err.Clear
        Err.Clear
        If Not taken Then Exit Do
        suffix = suffix + 1
        candidate = baseName & "_" & CStr(suffix)
    Loop
    GetUniqueBodyName = candidate
End Function

'------------------------------------------------------------------
' First free Remove_I001 / _2 / _3 ... name among the features of
' the target body.
'------------------------------------------------------------------
Function GetUniqueFeatureName(targetBody, baseName)
    On Error Resume Next
    Dim shapes
    Dim candidate
    Dim suffix
    Dim i
    Dim taken

    candidate = baseName
    On Error Resume Next
    Set shapes = targetBody.Shape
    Err.Clear
    If shapes Is Nothing Then
        GetUniqueFeatureName = candidate
        Exit Function
    End If

    suffix = 1
    Do
        taken = False
        On Error Resume Next
        For i = 1 To shapes.count
            If StrComp(ShapeName(shapes.item(i)), candidate, vbTextCompare) = 0 Then
                taken = True
                Exit For
            End If
        Next
        Err.Clear
        If Not taken Then Exit Do
        suffix = suffix + 1
        candidate = baseName & "_" & CStr(suffix)
    Loop
    GetUniqueFeatureName = candidate
End Function

Function ShapeName(feature)
    On Error Resume Next
    On Error Resume Next
    ShapeName = CStr(feature.name)
    Err.Clear
End Function


' ============================================================
' Boolean Remove - Paste Special "As Result, with out link"
' ============================================================
' Selection.PasteSpecial exists on every CATIA V5 release, but the
' PasteSpecialMode property only came later, so the mode is set
' defensively: named enum first, numeric enum second, plain paste
' last. The caller verifies the outcome by counting bodies, which is
' the only proof that really matters.
' ============================================================
Function PasteBodyAsResult(selectionObject)
    On Error Resume Next
    Dim errNo

    On Error Resume Next
    Err.Clear
    selectionObject.PasteSpecial PASTE_MODE_NOLINK
    errNo = Err.Number
    Err.Clear

    If errNo <> 0 Then
        selectionObject.PasteSpecialMode = 2
        selectionObject.PasteSpecial
        errNo = Err.Number
        Err.Clear
    End If

    If errNo <> 0 Then
        selectionObject.PasteSpecial
        errNo = Err.Number
        Err.Clear
    End If
    Err.Clear

    PasteBodyAsResult = (errNo = 0)
End Function

'------------------------------------------------------------------
' Locates the body created by Paste Special. The pasted body is
' appended to part.bodies, so the newest one that is neither the
' tool nor the target is the result. Selection is used as a
' fallback because CATIA leaves the pasted body selected.
'------------------------------------------------------------------
Function FindNewBodyAfterPaste(bodiesCollection, _
                                       bodyCountBefore, _
                                       sourceBody, _
                                       targetBody, _
                                       selectionObject)
    On Error Resume Next
    Dim i
    Dim candidate

    For i = bodiesCollection.count To bodyCountBefore + 1 Step -1
        On Error Resume Next
        Set candidate = bodiesCollection.item(i)
        Err.Clear
        If Not candidate Is Nothing Then
            If Not (candidate Is sourceBody) And Not (candidate Is targetBody) Then
                Set FindNewBodyAfterPaste = candidate
                Exit Function
            End If
        End If
    Next

    If selectionObject Is Nothing Then Exit Function
    On Error Resume Next
    If selectionObject.count > 0 Then
        Set candidate = selectionObject.item(1).value
        If Not candidate Is Nothing Then
            If Not (candidate Is sourceBody) And Not (candidate Is targetBody) Then
                Set FindNewBodyAfterPaste = candidate
            End If
        End If
    End If
    Err.Clear
End Function


' ============================================================
' Boolean Remove - body picker (native CATIA prompt)
' ============================================================
' The dashboard is top-most while it runs, which would cover the
' graphics window, so the top-most flag is released for the duration
' of the prompt and restored afterwards - success or cancel.
' ============================================================
Function SelectBodyFromUser(part, _
                                    windowTitle, _
                                    promptText, _
                                    ByRef pickedBody)
    On Error Resume Next
    Dim selectionObject
    Dim result
    Dim pickedName

    SelectBodyFromUser = False
    Set pickedBody = Nothing

    On Error Resume Next
    Set selectionObject = CATIA.ActiveDocument.Selection
    Err.Clear
    If selectionObject Is Nothing Then Exit Function

    ReleaseTopmost windowTitle
    On Error Resume Next
    selectionObject.Clear
    Err.Clear

    result = ""
    On Error Resume Next
    result = selectionObject.SelectElement2(Array("Body"), promptText, False)
    Err.Clear

    If StrComp(result, "Normal", vbTextCompare) <> 0 Then
        MakeTopmost windowTitle
        Exit Function
    End If

    On Error Resume Next
    Set pickedBody = selectionObject.item(1).value
    pickedName = CStr(pickedBody.name)
    Err.Clear
    On Error Resume Next
    selectionObject.Clear
    Err.Clear

    MakeTopmost windowTitle

    If pickedBody Is Nothing Then Exit Function
    If Len(Trim(pickedName)) = 0 Then Exit Function
    If Not IsBodyObjectUsable(part, pickedBody) Then Exit Function

    SelectBodyFromUser = True
End Function

'------------------------------------------------------------------
' Dashboard action: store the body the user picked as the copy body
' or the target body of one instance, then report the name back so
' the slot fills in.
'------------------------------------------------------------------
Sub ChooseInstanceBody(part, data, rsp, windowTitle)
    On Error Resume Next
    Dim isCopyBody
    Dim instanceIndex
    Dim promptText
    Dim pickedBody
    Dim pickedName
    Dim otherBody
    Dim otherName

    On Error Resume Next

    EnsureBodyCollections
    isCopyBody = (StrComp(ReadKey(data, "WHICH"), "COPY", vbTextCompare) = 0)
    instanceIndex = ReadInstance(data)
    If instanceIndex < 1 Then instanceIndex = 1

    If isCopyBody Then
        promptText = "Select the COPY BODY (the tool) for Instance " & InstanceTag(instanceIndex) & "..."
    Else
        promptText = "Select the TARGET BODY (the body to cut) for Instance " & InstanceTag(instanceIndex) & "..."
    End If

    If Not SelectBodyFromUser(part, windowTitle, promptText, pickedBody) Then
        SendBooleanResponse rsp, "CANCELLED", instanceIndex, "", "", "", "No body selected."
        Exit Sub
    End If

    pickedName = CStr(pickedBody.name)

    ' A body cannot be both the tool and the target of the same cut.
    If isCopyBody Then
        Set otherBody = GetStoredObject(gTargetBodyObjects, instanceIndex)
    Else
        Set otherBody = GetStoredObject(gCopyBodyObjects, instanceIndex)
    End If
    If Not otherBody Is Nothing Then
        If IsBodyObjectUsable(part, otherBody) Then
            If AreSameCATIAObject(part, pickedBody, otherBody) Then
                otherName = CStr(otherBody.name)
                SendBooleanResponse rsp, "FAILED", instanceIndex, "", "", "", "This body is already the other body of Instance " & InstanceTag(instanceIndex) & " (" & otherName & ")."
                Exit Sub
            End If
        End If
    End If

    If isCopyBody Then
        SetStoredObject gCopyBodyObjects, instanceIndex, pickedBody
        SetStoredText gCopyBodyNames, instanceIndex, pickedName
    Else
        SetStoredObject gTargetBodyObjects, instanceIndex, pickedBody
        SetStoredText gTargetBodyNames, instanceIndex, pickedName
    End If

    If isCopyBody Then
        SendBooleanResponse rsp, "OK", instanceIndex, pickedName, "", "", "Copy body stored for Instance " & InstanceTag(instanceIndex) & "."
    Else
        SendBooleanResponse rsp, "OK", instanceIndex, "", pickedName, "", "Target body stored for Instance " & InstanceTag(instanceIndex) & "."
    End If

    If Err.Number <> 0 Then
        SendBooleanResponse rsp, "FAILED", instanceIndex, "", "", "", "Body selection failed: " & Err.Description
        Err.Clear
    End If
End Sub


' ============================================================
' Boolean Remove - the operation itself
' ============================================================
' copy body -> Copy -> select target body -> Paste Special As Result
' -> rename the pasted body REMOVE_TOOL_Ixxx -> InWorkObject = target
' -> ShapeFactory.AddNewRemove -> name the feature Remove_Ixxx.
'
' The in-work object is restored on the way out, whatever happened,
' and the selection is left on the new Remove feature so the user
' can see what was created.
' ============================================================
Sub RunBooleanRemove(part1, _
                             rsp, _
                             instanceIndex)
    On Error Resume Next
    Dim statusText
    If RunBooleanRemoveCore(part1, instanceIndex, statusText) Then
        SendBooleanResponse rsp, "OK", instanceIndex, "", "", ExtractFeatureName(statusText), statusText
    Else
        SendBooleanResponse rsp, "FAILED", instanceIndex, "", "", "", statusText
    End If
End Sub

'------------------------------------------------------------------
' Same engine without the file response, so REMOVE ALL can loop it
' and write one summary line at the end. Returns the human readable
' outcome in statusText.
'------------------------------------------------------------------
Function RunBooleanRemoveCore(part1, instanceIndex, ByRef statusText)
    On Error Resume Next

    EnsureBodyCollections

    Dim sourceBody, targetBody, resultBody
    Dim bodiesCollection, selectionObject, shapeFactoryObject
    Dim removeFeature, savedWorkObject
    Dim bodyCountBefore, bodyCountAfter
    Dim toolName, removeName, featureName, tag

    RunBooleanRemoveCore = False
    tag = InstanceTag(instanceIndex)
    Set savedWorkObject = Nothing

    Set sourceBody = GetStoredObject(gCopyBodyObjects, instanceIndex)
    Set targetBody = GetStoredObject(gTargetBodyObjects, instanceIndex)

    If sourceBody Is Nothing Then
        statusText = "No copy body is stored for Instance " & tag & ". Select the copy body first."
        Exit Function
    End If

    If targetBody Is Nothing Then
        statusText = "No target body is stored for Instance " & tag & ". Select the target body first."
        Exit Function
    End If

    If AreSameCATIAObject(part1, sourceBody, targetBody) Then
        statusText = "Copy body and target body cannot be the same body (Instance " & tag & ")."
        Exit Function
    End If

    If Not IsBodyObjectUsable(part1, sourceBody) Then
        ClearStoredBody gCopyBodyObjects, gCopyBodyNames, instanceIndex
        statusText = "The stored copy body of Instance " & tag & " is no longer available. Select the copy body again."
        Exit Function
    End If

    If Not IsBodyObjectUsable(part1, targetBody) Then
        ClearStoredBody gTargetBodyObjects, gTargetBodyNames, instanceIndex
        statusText = "The stored target body of Instance " & tag & " is no longer available. Select the target body again."
        Exit Function
    End If

    Err.Clear
    Set bodiesCollection = part1.Bodies
    Set selectionObject = CATIA.ActiveDocument.Selection
    bodyCountBefore = bodiesCollection.Count
    If Err.Number <> 0 Then
        statusText = "Boolean Remove failed for Instance " & tag & ": " & Err.Description
        Err.Clear
        Exit Function
    End If

    ' ----- copy the tool body -----
    selectionObject.Clear
    selectionObject.Add sourceBody
    selectionObject.Copy

    ' ----- paste it into the target as a standalone result -----
    selectionObject.Clear
    selectionObject.Add targetBody
    If Not PasteBodyAsResult(selectionObject) Then
        statusText = "Boolean Remove failed for Instance " & tag & ": CATIA could not paste the selected copy body as a result."
        RestoreWorkObject part1, savedWorkObject
        Err.Clear
        Exit Function
    End If

    part1.Update
    Err.Clear
    bodyCountAfter = bodiesCollection.Count
    If bodyCountAfter <= bodyCountBefore Then
        statusText = "Boolean Remove failed for Instance " & tag & ": no new result body was created by Paste Special."
        RestoreWorkObject part1, savedWorkObject
        Err.Clear
        Exit Function
    End If

    Set resultBody = FindNewBodyAfterPaste(bodiesCollection, bodyCountBefore, sourceBody, targetBody, selectionObject)
    If resultBody Is Nothing Then
        statusText = "Boolean Remove failed for Instance " & tag & ": the pasted result body could not be identified."
        RestoreWorkObject part1, savedWorkObject
        Err.Clear
        Exit Function
    End If

    ' ----- name the tool body, keep the CATIA name if renaming fails -----
    toolName = GetUniqueBodyName(bodiesCollection, "REMOVE_TOOL_I" & tag)
    Err.Clear
    resultBody.Name = toolName
    If Err.Number <> 0 Then
        Err.Clear
        toolName = CStr(resultBody.Name)
        Err.Clear
    End If

    ' ----- cut it out of the target body -----
    Set savedWorkObject = part1.InWorkObject
    Err.Clear
    part1.InWorkObject = targetBody

    Set shapeFactoryObject = part1.ShapeFactory
    Set removeFeature = shapeFactoryObject.AddNewRemove(resultBody)
    If Err.Number <> 0 Or removeFeature Is Nothing Then
        statusText = "Boolean Remove failed for Instance " & tag & ": " & Err.Description
        Err.Clear
        RestoreWorkObject part1, savedWorkObject
        CATIA.ActiveDocument.Selection.Clear
        Err.Clear
        Exit Function
    End If

    removeName = GetUniqueFeatureName(targetBody, "Remove_I" & tag)
    featureName = removeName
    Err.Clear
    removeFeature.Name = removeName
    If Err.Number <> 0 Then
        Err.Clear
        featureName = "Remove_I" & tag & "_" & StampText("hhnnss")
        removeFeature.Name = featureName
        Err.Clear
    End If

    ' ----- leave the part the way it was found -----
    RestoreWorkObject part1, savedWorkObject

    part1.Update
    Err.Clear

    selectionObject.Clear
    selectionObject.Add removeFeature
    Err.Clear

    statusText = "Boolean Remove completed for Instance " & tag & _
                 ". Source: " & CStr(sourceBody.Name) & _
                 " | Target: " & CStr(targetBody.Name) & _
                 " | Feature: " & featureName
    Err.Clear
    RunBooleanRemoveCore = True
End Function

'------------------------------------------------------------------
' Puts the in-work object back the way it was found, whatever
' happened during the Boolean Remove.
'------------------------------------------------------------------
Sub RestoreWorkObject(part1, savedWorkObject)
    On Error Resume Next
    If Not savedWorkObject Is Nothing Then part1.InWorkObject = savedWorkObject
    Err.Clear
End Sub


'------------------------------------------------------------------
' Pulls the "Feature: xxx" part out of the completion text so the
' dashboard can show the feature name on its own.
'------------------------------------------------------------------
Function ExtractFeatureName(statusText)
    On Error Resume Next
    Dim position
    position = InStrRev(statusText, "Feature: ")
    If position = 0 Then Exit Function
    ExtractFeatureName = Trim(Mid(statusText, position + 9))
End Function

'------------------------------------------------------------------
' Writes the Boolean Remove reply. Separate keys from SendResponse
' so a body/feature answer never disturbs the parameter readout:
'   BSTATUS = OK | FAILED | CANCELLED | PARTIAL
'   BINST   = instance index the answer belongs to
'   BCOPY / BTARGET = stored body names (slot refresh)
'   BFEATURE = name of the Remove feature that was created
'   BMSG    = text for the status bar
'------------------------------------------------------------------
Sub SendBooleanResponse(path, _
                                statusText, _
                                instanceIndex, _
                                copyName, _
                                targetName, _
                                featureName, _
                                messageText)
    On Error Resume Next
    On Error Resume Next
    Dim f
    DeleteFile path
    Set f = NewWriter(path)
    If f Is Nothing Then Exit Sub
    f.WriteLine "BSTATUS=" & statusText
    f.WriteLine "BINST=" & CStr(instanceIndex)
    f.WriteLine "BCOPY=" & copyName
    f.WriteLine "BTARGET=" & targetName
    f.WriteLine "BFEATURE=" & featureName
    f.WriteLine "BMSG=" & messageText
    f.Close
    Err.Clear
End Sub

'------------------------------------------------------------------
' Releases the top-most flag so the user can reach the CATIA
' graphics window during a native selection prompt. MakeTopmost
' puts it back afterwards.
'------------------------------------------------------------------
Sub ReleaseTopmost(title)
    On Error Resume Next
    ' VBScript cannot call SetWindowPos, so the CATIA window is pulled to
    ' the front instead: the user can reach the graphics area for the
    ' native selection prompt, and MakeTopmost brings the HTA back after.
    gShell.AppActivate "CATIA"
    SleepMs 120
    Err.Clear
End Sub

'------------------------------------------------------------------
' Command dispatcher for the BOOLEAN REMOVE card. Kept apart from
' the parameter commands so the dashboard protocol stays readable:
'   SELECTBODY  WHICH=COPY|TARGET   INSTANCE=n
'   REMOVEONE                       INSTANCE=n
'------------------------------------------------------------------
Sub HandleBooleanCommand(part, _
                                 action, _
                                 data, _
                                 rsp, _
                                 windowTitle)
    On Error Resume Next
    Select Case action
        Case "SELECTBODY"
            ChooseInstanceBody part, data, rsp, windowTitle
        Case "REMOVEONE"
            RunBooleanRemove part, rsp, ReadInstance(data)
    End Select
End Sub

'------------------------------------------------------------------
' Read-only slot showing which body is stored for this instance,
' with its own pick button (the native CATIA prompt).
'------------------------------------------------------------------
Sub WriteBodySlot(f, id, label, which, hintText)
    On Error Resume Next
    W f, "<div class='field'><div class='label'>" & H(label) & " <span class='auto'>CATIA</span></div><div class='row'>"
    W f, "<input type='text' id='" & id & "' value='' readonly class='ro bodySlot'><div class='unit'>body</div></div>"
    W f, "<div class='row'><button class='pickBtn' onclick='pickBody(" & QuoteText(which) & ")'>Select in CATIA</button></div>"
    W f, "<div class='hint'>" & H(hintText) & "</div></div>"
End Sub
' ============================================================
' Dashboard v2 - Lifter Studio
' ============================================================

Function ReadInstance(data)
    On Error Resume Next
    Dim text, value
    value = 0
    text = ReadKey(data, "INSTANCE")
    If IsNumeric(text) Then value = CLng(text)
    If value < 1 Then value = 1
    ReadInstance = value
    Err.Clear
End Function

Sub StartPowerCopy()
    On Error Resume Next
    On Error Resume Next
    Err.Clear
    CATIA.StartCommand "Instantiate From Document"
    If Err.Number = 0 Then Exit Sub
    Err.Clear
    CATIA.StartCommand "Instantiate from Document"
    If Err.Number = 0 Then Exit Sub
    Err.Clear
    CATIA.StartCommand "PowerCopy Instantiation"
    If Err.Number <> 0 Then
        MsgBox "CATIA could not start Instantiate From Document.", vbExclamation, APP_TITLE
    End If
End Sub

Sub UpdateValues(part, data, rsp, instanceIndex)
    On Error Resume Next
    Dim undercutSet, headSet
    Dim a, b, c, d, e
    Dim problem

    problem = ""
    Set undercutSet = GetUndercutSet(part, instanceIndex)
    Set headSet = GetHeadSet(part, instanceIndex)

    ' Templates do not all group the parameters the same way (some keep
    ' HAS_EXTERNAL_FACE next to UNDERCUT_LENGTH), so every parameter is
    ' resolved in its expected set first and then anywhere in the tree.
    Set a = FindInstanceParam(part, undercutSet, headSet, p1, instanceIndex)
    Set b = FindInstanceParam(part, undercutSet, headSet, p2, instanceIndex)
    Set c = FindInstanceParam(part, undercutSet, headSet, P3, instanceIndex)
    Set d = FindInstanceParam(part, undercutSet, headSet, P4, instanceIndex)
    Set e = FindInstanceParam(part, headSet, undercutSet, P5, instanceIndex)

    problem = MissingList(part, a, b, c, d, e)

    If Len(problem) > 0 Then
        MsgBox "Parameter update failed." & vbCrLf & problem, vbCritical, APP_TITLE
        Err.Clear
        Exit Sub
    End If

    Err.Clear
    CATIA.RefreshDisplay = False
    problem = SetDimension(part, a, ReadKey(data, p1), "mm")
    If Len(problem) = 0 Then problem = SetDimension(part, b, ReadKey(data, p2), "deg")
    If Len(problem) = 0 Then problem = SetDimension(part, c, ReadKey(data, P3), "deg")
    Dim wantedBool
    wantedBool = (LCase(Trim(ReadKey(data, P4))) = "true")
    If Len(problem) = 0 Then problem = SetBooleanValue(part, d, ReadKey(data, P4))
    If Len(problem) = 0 Then problem = SetDimension(part, e, ReadKey(data, P5), "mm")

    If Len(problem) = 0 Then
        part.Update
        If Err.Number <> 0 Then
            problem = Err.Description
            Err.Clear
        End If
    End If

    ' The update itself can revert a Boolean that is driven by a rule or a
    ' formula: check the value that really survived and say so.
    If Len(problem) = 0 Then
        If BoolValueOf(d) <> wantedBool Then
            problem = "CATIA reset " & P4 & " to " & LCase(CStr(BoolValueOf(d))) & _
                      " during the update. It is driven by a formula, a rule or a design table."
        End If
    End If

    CATIA.RefreshDisplay = True
    Err.Clear

    If Len(problem) > 0 Then
        MsgBox "Parameter update failed." & vbCrLf & problem, vbCritical, APP_TITLE
        ' Re-send the real values so the dashboard never shows a state the
        ' CATPart does not have (a Boolean that CATIA refused, for example).
        SendValues part, rsp, instanceIndex
        Exit Sub
    End If

    SendValues part, rsp, instanceIndex
End Sub

'------------------------------------------------------------------
' Both setters return "" on success, or the reason of the failure -
' VBScript has no On Error GoTo, so the caller checks the text.
'------------------------------------------------------------------
Function SetDimension(part, parameter, rawValue, unitName)
    On Error Resume Next
    Dim blocked
    SetDimension = ""
    If parameter Is Nothing Then
        SetDimension = "A dashboard parameter was not found."
        Exit Function
    End If
    If Len(Trim(rawValue)) = 0 Then
        SetDimension = "A dashboard value is empty."
        Exit Function
    End If

    ' A dimension can be formula driven too.
    blocked = TakeControlOfParameter(part, parameter, LeafName(CStr(parameter.Name)))
    If Len(blocked) > 0 Then
        SetDimension = blocked
        Exit Function
    End If

    Err.Clear
    parameter.ValuateFromString Replace(Trim(rawValue), ",", ".") & unitName
    If Err.Number <> 0 Then
        SetDimension = Err.Description
        Err.Clear
    End If
End Function

'------------------------------------------------------------------
' Writing a CATIA Boolean parameter is not a single call that always
' works: the property assignment can be silently ignored, and a
' formula driving the parameter always wins. Every attempt is
' therefore verified by reading the value back.
'------------------------------------------------------------------
Function SetBooleanValue(part, parameter, rawValue)
    On Error Resume Next
    Dim text, wanted, message, relation, attempt

    SetBooleanValue = ""
    If parameter Is Nothing Then
        SetBooleanValue = P4 & " was not found on this instance."
        Exit Function
    End If

    text = LCase(Trim(rawValue))
    If text = "true" Then
        wanted = True
    ElseIf text = "false" Then
        wanted = False
    Else
        SetBooleanValue = "Invalid Boolean value."
        Exit Function
    End If

    If BoolValueOf(parameter) = wanted Then Exit Function      ' nothing to do

    ' A formula driving the parameter always wins: offer to switch it off.
    message = TakeControlOfParameter(part, parameter, P4)
    If Len(message) > 0 Then
        SetBooleanValue = message
        Exit Function
    End If
    message = ""

    ' 1) the normal way
    Err.Clear
    parameter.Value = wanted
    message = Err.Description
    Err.Clear
    If BoolValueOf(parameter) = wanted Then Exit Function

    ' 2) string valuation, in the spellings CATIA accepts
    For attempt = 1 To 3
        Err.Clear
        If attempt = 1 Then parameter.ValuateFromString text
        If attempt = 2 Then parameter.ValuateFromString UCase(Left(text, 1)) & Mid(text, 2)
        If attempt = 3 Then
            If wanted Then
                parameter.ValuateFromString "1"
            Else
                parameter.ValuateFromString "0"
            End If
        End If
        If Len(Err.Description) > 0 Then message = Err.Description
        Err.Clear
        If BoolValueOf(parameter) = wanted Then Exit Function
    Next

    SetBooleanValue = P4 & " could not be set to " & text & _
                      " (CATIA keeps " & LCase(CStr(BoolValueOf(parameter))) & ")."
    If Len(message) > 0 Then SetBooleanValue = SetBooleanValue & " " & message
End Function

'------------------------------------------------------------------
' A parameter driven by a formula cannot be edited: CATIA recomputes
' it on the next update. The user is asked once per formula whether
' the dashboard may deactivate it (the formula stays in the part and
' can be switched back on in CATIA at any time).
' Returns "" when the parameter is writable, otherwise the reason.
'------------------------------------------------------------------
Function TakeControlOfParameter(part, parameter, label)
    On Error Resume Next
    Dim relation, relationName, answer, message

    TakeControlOfParameter = ""
    If part Is Nothing Or parameter Is Nothing Then Exit Function

    Set relation = Nothing
    Err.Clear
    Set relation = GetFormulaFor(part.Relations, parameter)
    Err.Clear
    If relation Is Nothing Then Exit Function

    relationName = "a formula"
    relationName = CStr(relation.Name)
    Err.Clear

    answer = MsgBox(label & " is driven by the formula """ & relationName & """." & vbCrLf & vbCrLf & _
                    "Deactivate that formula so the dashboard can drive the value?" & vbCrLf & _
                    "The formula stays in the part and can be reactivated in CATIA " & _
                    "(right-click the relation > Deactivate/Activate).", _
                    vbYesNo + vbQuestion, APP_TITLE)

    If answer <> vbYes Then
        TakeControlOfParameter = label & " stays driven by the formula """ & relationName & """."
        Exit Function
    End If

    Err.Clear
    relation.Deactivate
    If Err.Number <> 0 Then
        message = Err.Description
        Err.Clear
        ' Older releases expose Activate/Deactivate only on the relation
        ' collection: try the documented alternative before giving up.
        part.Relations.Item(relationName).Deactivate
        If Err.Number <> 0 Then
            Err.Clear
            TakeControlOfParameter = "The formula """ & relationName & """ could not be deactivated. " & message
            Exit Function
        End If
    End If
    Err.Clear
End Function

'------------------------------------------------------------------
' Reads a CATIA Boolean parameter whatever its flavour.
'------------------------------------------------------------------
Function BoolValueOf(parameter)
    On Error Resume Next
    Dim v, s
    BoolValueOf = False
    If parameter Is Nothing Then Exit Function

    Err.Clear
    v = parameter.Value
    If Err.Number = 0 Then
        Err.Clear
        BoolValueOf = CBool(v)
        If Err.Number = 0 Then Exit Function
    End If

    Err.Clear
    s = LCase(Trim(CStr(parameter.ValueAsString)))
    Err.Clear
    BoolValueOf = (s = "true" Or s = "1" Or s = "yes")
End Function

Sub SendValues(part, rsp, instanceIndex)
    On Error Resume Next
    Dim undercutSet, headSet
    Dim a, b, c, d, e
    Dim rootStroke
    Set undercutSet = GetUndercutSet(part, instanceIndex)
    Set headSet = GetHeadSet(part, instanceIndex)

    Set a = FindInstanceParam(part, undercutSet, headSet, p1, instanceIndex)
    Set b = FindInstanceParam(part, undercutSet, headSet, p2, instanceIndex)
    Set c = FindInstanceParam(part, undercutSet, headSet, P3, instanceIndex)
    Set d = FindInstanceParam(part, undercutSet, headSet, P4, instanceIndex)
    Set e = FindInstanceParam(part, headSet, undercutSet, P5, instanceIndex)
    If a Is Nothing Or b Is Nothing Or c Is Nothing Then
        SendResponse rsp, "INCOMPLETE", "", "", "", "", "", "", "", ""
        Exit Sub
    End If
    If d Is Nothing Or e Is Nothing Then
        SendResponse rsp, "INCOMPLETE", "", "", "", "", "", "", "", ""
        Exit Sub
    End If

    ' v2 extra readouts: root STROKE_Distance + this instance's Draft
    On Error Resume Next
    Set rootStroke = part.parameters.item(P_STROKE)
    Err.Clear
    Dim strokeText, draftText, draftDiag
    strokeText = ""
    If Not rootStroke Is Nothing Then strokeText = ValueOnly(rootStroke)

    ' Draft display value: computed from the formula inputs so the field
    ' ALWAYS shows the formula result, even when the Draft parameter or
    ' its formula is missing on this part.
    GetDraftDisplay part, headSet, draftText, draftDiag

    SendResponse rsp, "OK", ValueOnly(a), ValueOnly(b), ValueOnly(c), BooleanText(d), ValueOnly(e), strokeText, draftText, draftDiag
End Sub


'------------------------------------------------------------------
' Draft readout (dashboard display)
'------------------------------------------------------------------
' 1) Preferred: compute the formula value directly from the two inputs
'       min( floor( atan( ( UNDERCUT_LENGTH + 5mm ) / STROKE_Distance ) * 180/PI + 0.5 ), 15 )
' 2) Fallback: read the Draft parameter itself.
' 3) Otherwise: "-" (no value to show).
' draftDiag tells the dashboard which source was used.
'------------------------------------------------------------------
Sub GetDraftDisplay(part, headSet, ByRef draftText, ByRef draftDiag)
    On Error Resume Next

    draftText = "-"
    draftDiag = "draft not available"

    Dim undercutP, strokeP, draftP
    Dim rootStroke
    Dim uVal, sVal, uOk, sOk

    Set undercutP = Nothing
    Set strokeP = Nothing
    Set draftP = Nothing
    Set rootStroke = Nothing
    On Error Resume Next
    Set rootStroke = part.parameters.item(P_STROKE)
    If Not headSet Is Nothing Then
        Set undercutP = FindDirect(headSet, P5)
        Set strokeP = FindDirect(headSet, P_STROKE)
        Set draftP = FindDirect(headSet, P_DRAFT)
    End If
    Err.Clear

    ' 1) compute from the formula inputs (always matches the molding rule)
    uOk = NumericValue(undercutP, uVal)
    If strokeP Is Nothing Then
        sOk = NumericValue(rootStroke, sVal)
    Else
        sOk = NumericValue(strokeP, sVal)
    End If
    If uOk And sOk And sVal > 0 Then
        draftText = CStr(ComputeDraftValue(uVal, sVal))
        draftDiag = "draft from formula"
        Exit Sub
    End If

    ' 2) fallback: the Draft parameter itself
    If Not draftP Is Nothing Then
        On Error Resume Next
        draftText = ValueOnly(draftP)
        Err.Clear
        If Len(Trim(draftText)) = 0 Then draftText = "-"
        draftDiag = "draft from parameter"
        Exit Sub
    End If

    If Err.Number <> 0 Then
        Err.Clear
        draftText = "-"
        draftDiag = "draft not available"
    End If
End Sub


'------------------------------------------------------------------
' Replicates the CATIA Draft formula on two numeric values (both mm):
'   min( floor( atan( ( U + 5mm ) / S ) * 180/PI + 0.5 ), 15 )
'------------------------------------------------------------------
Function ComputeDraftValue(undercutMM, strokeMM)
    On Error Resume Next
    Dim raw
    raw = Atn((undercutMM + 5.0) / strokeMM) * 180.0 / 3.14159265358979
    raw = Int(raw + 0.5)
    If raw > DRAFT_MAX_DEG Then raw = DRAFT_MAX_DEG
    ComputeDraftValue = raw
End Function


'------------------------------------------------------------------
' Reads a CATIA parameter as a Double (MKS: Length comes back in mm).
' Returns False when the parameter is Nothing or unreadable.
'------------------------------------------------------------------
Function NumericValue(parameter, ByRef outValue)
    On Error Resume Next
    If parameter Is Nothing Then Exit Function
    On Error Resume Next
    outValue = CDbl(parameter.value)
    If Err.Number = 0 Then NumericValue = True
    Err.Clear
End Function

Function GetUndercutSets(part)
    On Error Resume Next
    Dim result
    Set result = NewStore()
    CollectUndercutSets part.Parameters.RootParameterSet, result
    Set GetUndercutSets = result
    Err.Clear
End Function

Sub CollectUndercutSets(parentSet, result)
    On Error Resume Next
    Dim childSets, childSet, index
    On Error Resume Next
    Set childSets = parentSet.ParameterSets
    Err.Clear
    If childSets Is Nothing Then Exit Sub

    For index = 1 To childSets.count
        Set childSet = childSets.item(index)
        If IsUndercutSet(childSet) Then result.Add result.Count + 1, childSet
        CollectUndercutSets childSet, result
    Next
End Sub

Function IsUndercutSet(parameterSet)
    On Error Resume Next
    Dim a, b, c, d
    Set a = FindDirect(parameterSet, p1)
    Set b = FindDirect(parameterSet, p2)
    Set c = FindDirect(parameterSet, P3)
    Set d = FindDirect(parameterSet, P4)
    IsUndercutSet = Not a Is Nothing And Not b Is Nothing And Not c Is Nothing And Not d Is Nothing
End Function

Function GetHeadSets(part)
    On Error Resume Next
    Dim result
    Set result = NewStore()
    CollectHeadSets part.Parameters.RootParameterSet, result
    Set GetHeadSets = result
    Err.Clear
End Function

Sub CollectHeadSets(parentSet, result)
    On Error Resume Next
    Dim childSets, childSet, index
    On Error Resume Next
    Set childSets = parentSet.ParameterSets
    Err.Clear
    If childSets Is Nothing Then Exit Sub

    For index = 1 To childSets.count
        Set childSet = childSets.item(index)
        If Not FindDirect(childSet, P5) Is Nothing Then result.Add result.Count + 1, childSet
        CollectHeadSets childSet, result
    Next
End Sub

Function GetUndercutSet(part, instanceIndex)
    On Error Resume Next
    Dim sets
    Set sets = GetUndercutSets(part)
    If instanceIndex < 1 Then instanceIndex = 1
    If instanceIndex <= sets.count Then Set GetUndercutSet = sets.item(instanceIndex)
End Function

Function GetHeadSet(part, instanceIndex)
    On Error Resume Next
    Dim sets
    Set sets = GetHeadSets(part)
    If instanceIndex < 1 Then instanceIndex = 1
    If instanceIndex <= sets.count Then Set GetHeadSet = sets.item(instanceIndex)
End Function

Function InstanceCount(part)
    On Error Resume Next
    Dim undercutSets, headSets, value
    Set undercutSets = GetUndercutSets(part)
    Set headSets = GetHeadSets(part)
    value = undercutSets.Count
    If headSets.Count < value Then value = headSets.Count
    InstanceCount = value
    Err.Clear
End Function

'------------------------------------------------------------------
' Strict lookup INSIDE one parameter set.
' CATIA's DirectParameters.Item(name) resolves names loosely (it can
' answer with an element that lives somewhere else, which made a set
' named UNDERCUT_LENGTH look like it owned a parameter with the same
' name). The leaf names are therefore compared explicitly.
'------------------------------------------------------------------
Function FindDirect(parameterSet, wantedName)
    On Error Resume Next
    Dim parameters, parameter, index
    Set FindDirect = Nothing
    If parameterSet Is Nothing Then Exit Function

    Set parameters = Nothing
    Set parameters = parameterSet.DirectParameters
    Err.Clear
    If parameters Is Nothing Then Exit Function

    For index = 1 To parameters.Count
        Set parameter = Nothing
        Set parameter = parameters.Item(index)
        If Not parameter Is Nothing Then
            If StrComp(LeafName(CStr(parameter.Name)), wantedName, vbTextCompare) = 0 Then
                Set FindDirect = parameter
                Err.Clear
                Exit Function
            End If
        End If
    Next
    Err.Clear
End Function

Function LeafName(fullName)
    On Error Resume Next
    Dim position
    position = InStrRev(fullName, "\")
    If position > 0 Then fullName = Mid(fullName, position + 1)
    position = InStrRev(fullName, "/")
    If position > 0 Then fullName = Mid(fullName, position + 1)
    LeafName = Trim(fullName)
End Function

Function ValueOnly(parameter)
    On Error Resume Next
    Dim text
    text = CStr(parameter.ValueAsString)
    text = Replace(text, "mm", "", 1, -1, vbTextCompare)
    text = Replace(text, "deg", "", 1, -1, vbTextCompare)
    text = Replace(text, ChrW(176), "")
    ValueOnly = Trim(Replace(text, ",", "."))
End Function

Function BooleanText(parameter)
    On Error Resume Next
    If BoolValueOf(parameter) Then
        BooleanText = "true"
    Else
        BooleanText = "false"
    End If
    Err.Clear
End Function

Sub BuildDashboard(hta, cmd, rsp, docName, part, windowTitle, linkedCount, draftCount)
    On Error Resume Next
    Dim fileNumber
    Dim undercutSet, headSet
    Dim v1, v2, v3, v4, v5
    Dim rootStroke, v6, v7, v7Diag
    Dim bodyCopyName, bodyTargetName
    Dim count
    Set undercutSet = GetUndercutSet(part, 1)
    Set headSet = GetHeadSet(part, 1)
    If Not undercutSet Is Nothing Then
        v1 = SafeValue(undercutSet, p1)
        v2 = SafeValue(undercutSet, p2)
        v3 = SafeValue(undercutSet, P3)
        v4 = SafeBoolean(undercutSet, P4)
    End If
    If Not headSet Is Nothing Then v5 = SafeValue(headSet, P5)

    ' v2 readouts: stroke (root, single source of truth) + instance 1 draft
    v6 = ""
    v7 = "-"
    On Error Resume Next
    Set rootStroke = part.parameters.item(P_STROKE)
    Err.Clear
    If Not rootStroke Is Nothing Then v6 = ValueOnly(rootStroke)
    GetDraftDisplay part, headSet, v7, v7Diag

    ' Boolean Remove card: the pair already stored for instance 1, if any
    EnsureBodyCollections
    bodyCopyName = StoredInstanceName(part, True, 1)
    bodyTargetName = StoredInstanceName(part, False, 1)

    count = InstanceCount(part)

    Set fileNumber = NewWriter(hta)
    If fileNumber Is Nothing Then Exit Sub
    W fileNumber, "<html><head><title>" & H(windowTitle) & "</title>"
    W fileNumber, "<HTA:APPLICATION BORDER='thin' CAPTION='yes' SCROLL='yes' SINGLEINSTANCE='yes'>"
    W fileNumber, "<meta http-equiv='X-UA-Compatible' content='IE=9'>"
    WriteCss fileNumber
    WriteJs fileNumber, cmd, rsp, count, bodyCopyName, bodyTargetName
    W fileNumber, "</head><body onload='init()' onbeforeunload='closing()'>"

    ' ---------------- dark header ----------------
    W fileNumber, "<div class='top'>"
    W fileNumber, "<div class='logo'>L</div>"
    W fileNumber, "<div class='brand'><div class='bt'>Lifter Studio</div><div class='bs'>PowerCopy parameter control</div></div>"
    W fileNumber, "<div class='doc'>" & H(docName) & "</div>"
    W fileNumber, "<div class='conn'><span class='dot' id='connDot'></span><span id='connText'>Connected</span></div>"
    W fileNumber, "</div>"

    ' ---------------- summary tiles ----------------
    W fileNumber, "<div class='stats'>"
    W fileNumber, "<div class='stat'><div class='sv' id='statCount'>" & CStr(count) & "</div><div class='sl'>Instances</div></div>"
    W fileNumber, "<div class='stat'><div class='sv' id='statStroke'>" & H(v6) & "</div><div class='sl'>Stroke mm</div></div>"
    W fileNumber, "<div class='stat'><div class='sv' id='statDraft'>" & H(v7) & "</div><div class='sl'>Draft deg</div></div>"
    W fileNumber, "</div>"

    W fileNumber, "<div class='wrap'>"

    ' ---------------- sidebar: instance list ----------------
    W fileNumber, "<div class='rail'>"
    W fileNumber, "<div class='railTitle'>Power copy instances</div>"
    W fileNumber, "<div id='instList'></div>"
    W fileNumber, "<button class='pcBtn' onclick='powerCopy()'>+ Instantiate From Document</button>"
    W fileNumber, "<div class='railNote' id='railNote'></div>"
    W fileNumber, "</div>"

    ' ---------------- main column ----------------
    W fileNumber, "<div class='main'>"

    ' card 1: undercut depth
    W fileNumber, "<div class='card'>"
    W fileNumber, "<div class='secHead'>Undercut depth"
    W fileNumber, "<span class='pager'><a onclick='prevNext(-1)'>" & H(ChrW(8249)) & "</a><a onclick='prevNext(1)'>" & H(ChrW(8250)) & "</a></span>"
    W fileNumber, "<span class='tag' id='secTag'>Instance 001</span></div>"
    W fileNumber, "<div class='grid'>"
    WriteField fileNumber, "upper", "Upper internal distance", v1, "mm", "Tooling-side clearance"
    WriteField fileNumber, "vertical", "Internal vertical angle", v2, "deg", "0-90 typical"
    WriteField fileNumber, "horizontal", "Internal horizontal angle", v3, "deg", "0-90 typical"
    WriteBooleanField fileNumber, v4
    W fileNumber, "</div></div>"

    ' card 2: lifter head
    W fileNumber, "<div class='card'>"
    W fileNumber, "<div class='secHead'>Lifter head</div>"
    W fileNumber, "<div class='grid'>"
    WriteField fileNumber, "headLength", "Lifter head length", v5, "mm", ""
    WriteReadonlyField fileNumber, "stroke", "Stroke distance", v6, "mm", "Linked to main body", "AUTO"
    WriteReadonlyField fileNumber, "draft", "Draft angle", v7, "deg", "From formula", "MAX 15" & ChrW(176)
    W fileNumber, "</div></div>"

    ' card 3: boolean remove
    W fileNumber, "<div class='card'>"
    W fileNumber, "<div class='secHead'>Boolean remove"
    W fileNumber, "<span class='tag' id='rmTag'>Instance 001</span></div>"
    W fileNumber, "<div class='grid'>"
    WriteBodySlot fileNumber, "bodyCopy", "Copy body (tool)", "COPY", "Copied and pasted as result"
    WriteBodySlot fileNumber, "bodyTarget", "Target body (to cut)", "TARGET", "Receives the Remove feature"
    W fileNumber, "<div class='field'><div class='label'>Last result</div>"
    W fileNumber, "<div class='rmBox' id='rmInfo'>No remove executed yet.</div></div>"
    W fileNumber, "</div>"
    W fileNumber, "<div class='rmActions'>"
    W fileNumber, "<button class='apply rmOne' onclick='removeInstance()'>Remove this instance</button>"
    W fileNumber, "</div>"
    W fileNumber, "</div>"
    ' actions
    W fileNumber, "<div class='actions'>"
    W fileNumber, "<button onclick='closeDash()'>Close</button>"
    W fileNumber, "<button onclick='refreshData()'>Refresh</button>"
    W fileNumber, "<button class='apply' onclick='applyData()'>Apply and Update</button>"
    W fileNumber, "</div>"

    W fileNumber, "</div></div>"

    ' ---------------- status bar ----------------
    W fileNumber, "<div class='statusbar'><span class='dot' id='statusDot'></span><span id='statusText'>Ready - " & CStr(draftCount) & " draft formula(s), " & CStr(linkedCount) & " stroke link(s).</span>"
    W fileNumber, "<span id='dirty' class='dirty'>Unsaved changes</span></div>"

    ' ---------------- hand-off modal ----------------
    W fileNumber, "<div id='handoff' class='overlay'>"
    W fileNumber, "<div class='modal'>"
    W fileNumber, "<div class='modalTitle'>PowerCopy mode active</div>"
    W fileNumber, "<div class='modalBody'>Complete the insertion in CATIA, then close the dashboard.</div>"
    W fileNumber, "<button class='apply' onclick='closeAfter()'>Close Dashboard</button>"
    W fileNumber, "</div></div>"

    W fileNumber, "</body></html>"
    fileNumber.Close
End Sub

Sub WriteField(f, id, label, value, unitText, hintText)
    On Error Resume Next
    W f, "<div class='field'><div class='label'>" & H(label) & "</div><div class='row'>"
    W f, "<input type='text' id='" & id & "' value='" & H(value) & "' onkeyup='markDirty()'><div class='unit'>" & H(unitText) & "</div></div>"
    If Len(hintText) > 0 Then W f, "<div class='hint'>" & H(hintText) & "</div>"
    W f, "</div>"
End Sub

Sub WriteReadonlyField(f, id, label, value, unitText, hintText, badgeText)
    On Error Resume Next
    W f, "<div class='field'><div class='label'>" & H(label) & " <span class='auto'>" & H(badgeText) & "</span></div><div class='row'>"
    W f, "<input type='text' id='" & id & "' value='" & H(value) & "' readonly class='ro'><div class='unit'>" & H(unitText) & "</div></div>"
    If Len(hintText) > 0 Then W f, "<div class='hint'>" & H(hintText) & "</div>"
    W f, "</div>"
End Sub

Sub WriteBooleanField(f, value)
    On Error Resume Next
    Dim checked
    If LCase(value) = "true" Then checked = " checked"
    W f, "<div class='field'><div class='label'>Has external face</div><div class='boolRow'>"
    W f, "<label class='switch'><input type='checkbox' id='externalFace' onclick='syncBool()'" & checked & "><span class='knob'></span></label>"
    W f, "<span class='toggleTxt' id='boolText'></span></div>"
    W f, "<div class='hint'>Face visible on molded side</div></div>"
End Sub

Function SafeValue(parameterSet, parameterName)
    On Error Resume Next
    Dim parameter
    Set parameter = FindDirect(parameterSet, parameterName)
    If Not parameter Is Nothing Then SafeValue = ValueOnly(parameter)
End Function

Function SafeBoolean(parameterSet, parameterName)
    On Error Resume Next
    Dim parameter
    Set parameter = FindDirect(parameterSet, parameterName)
    If Not parameter Is Nothing Then SafeBoolean = BooleanText(parameter)
End Function

Sub SendResponse(path, Status, v1, v2, v3, v4, v5, v6, v7, diag)
    On Error Resume Next
    On Error Resume Next
    Dim f
    DeleteFile path
    Set f = NewWriter(path)
    If f Is Nothing Then Exit Sub
    f.WriteLine "STATUS=" & Status
    f.WriteLine "V1=" & v1
    f.WriteLine "V2=" & v2
    f.WriteLine "V3=" & v3
    f.WriteLine "V4=" & v4
    f.WriteLine "V5=" & v5
    f.WriteLine "V6=" & v6
    f.WriteLine "V7=" & v7
    f.WriteLine "DIAG=" & diag
    f.Close
    Err.Clear
End Sub

Function WaitCommand(path, seconds)
    On Error Resume Next
    Dim started
    WaitCommand = ""
    started = Now
    Do
        If FileExists(path) Then
            SleepMs 90
            If FileSize(path) > 0 Then
                WaitCommand = ReadAll(path)
                Err.Clear
                Exit Function
            End If
        End If
        If DateDiff("s", started, Now) >= seconds Then
            Err.Clear
            Exit Function
        End If
        SleepMs 200
    Loop
End Function

Function ReadKey(data, key)
    On Error Resume Next
    Dim lines, item, position, currentKey
    data = Replace(Replace(data, vbCrLf, vbLf), vbCr, vbLf)
    lines = Split(data, vbLf)
    For Each item In lines
        position = InStr(1, CStr(item), "=")
        If position > 0 Then
            currentKey = Trim(Left(CStr(item), position - 1))
            If StrComp(currentKey, key, vbTextCompare) = 0 Then
                ReadKey = Trim(Mid(CStr(item), position + 1))
                Exit Function
            End If
        End If
    Next
End Function

Sub MakeTopmost(title)
    On Error Resume Next
    Dim index
    For index = 1 To 40
        If gShell.AppActivate(title) Then
            Err.Clear
            Exit Sub
        End If
        SleepMs 120
    Next
    Err.Clear
End Sub

Sub PauseMs(milliseconds)
    SleepMs milliseconds
End Sub

Function FileExists(path)
    On Error Resume Next
    FileExists = False
    If Len(path) = 0 Then Exit Function
    FileExists = gFso.FileExists(path)
    Err.Clear
End Function

Function FileSize(path)
    On Error Resume Next
    FileSize = 0
    If Not gFso.FileExists(path) Then Exit Function
    FileSize = gFso.GetFile(path).Size
    Err.Clear
End Function

Sub DeleteFile(path)
    On Error Resume Next
    If Len(path) > 0 Then
        If gFso.FileExists(path) Then gFso.DeleteFile path, True
    End If
    Err.Clear
End Sub

Function ReadAll(path)
    On Error Resume Next
    Dim stream
    ReadAll = ""
    If Not gFso.FileExists(path) Then Exit Function
    Set stream = gFso.OpenTextFile(path, 1, False)
    If stream Is Nothing Then Exit Function
    If Not stream.AtEndOfStream Then ReadAll = stream.ReadAll
    stream.Close
    Err.Clear
End Function

Function NewWriter(path)
    On Error Resume Next
    Set NewWriter = Nothing
    Set NewWriter = gFso.CreateTextFile(path, True, False)
    Err.Clear
End Function

Sub W(f, text)
    On Error Resume Next
    f.WriteLine text
End Sub

Function QuoteText(text)
    On Error Resume Next
    QuoteText = Chr(34) & text & Chr(34)
End Function

Function JS(text)
    On Error Resume Next
    JS = Replace(Replace(text, "\", "\\"), "'", "\'")
End Function

Function H(text)
    On Error Resume Next
    text = Replace(text, "&", "&amp;")
    text = Replace(text, "<", "&lt;")
    text = Replace(text, ">", "&gt;")
    text = Replace(text, Chr(34), "&quot;")
    H = Replace(text, "'", "&#39;")
End Function


' ============================================================
' Dashboard v2 - CSS (IE9-safe: no flexbox, no CSS variables)
' ============================================================
Sub WriteCss(f)
    On Error Resume Next
    W f, "<style>"
    W f, "html,body{margin:0;padding:0;font-family:'Segoe UI',Arial,sans-serif;background:#edf1f5;color:#1d2d3c;font-size:12px}"
    W f, "body{overflow-y:auto;overflow-x:hidden}"
    W f, ".top{position:relative;height:56px;background:#10222e}"
    W f, ".logo{position:absolute;left:18px;top:11px;width:34px;height:34px;line-height:34px;text-align:center;background:#16a7b4;color:#fff;border-radius:9px;font-size:16px;font-weight:700}"
    W f, ".brand{position:absolute;left:64px;top:10px}.bt{color:#fff;font-size:15px;font-weight:600}.bs{color:#7e96a5;font-size:10px;margin-top:1px}"
    W f, ".doc{position:absolute;right:160px;top:17px;background:#1c3a4a;color:#a5d6de;padding:5px 12px;border-radius:12px;font-size:10px;max-width:280px;white-space:nowrap;overflow:hidden}"
    W f, ".conn{position:absolute;right:18px;top:20px;color:#a5d6de;font-size:10px}"
    W f, ".dot{display:inline-block;width:8px;height:8px;border-radius:50%;background:#43c46b;vertical-align:middle;margin-right:6px}"
    W f, ".dot.busy{background:#f0b64b}.dot.err{background:#e4574f}"
    W f, ".stats{padding:16px 20px 0}"
    W f, ".stat{display:inline-block;background:#fff;border:1px solid #dfe6ed;border-radius:10px;padding:10px 16px 9px;margin-right:10px;min-width:110px}"
    W f, ".sv{font-size:17px;font-weight:700;color:#10222e}.sl{font-size:9px;color:#7b8a9b;letter-spacing:1px;margin-top:2px}"
    W f, ".wrap{padding:12px 20px 16px}"
    W f, ".rail{float:left;width:232px;margin-right:14px}.main{margin-left:246px}"
    W f, ".railTitle{font-size:10px;font-weight:700;letter-spacing:1px;color:#7b8a9b;margin:4px 2px 8px}"
    W f, ".inst{background:#fff;border:1px solid #dfe6ed;border-radius:10px;padding:10px 13px;margin-bottom:7px;cursor:pointer}"
    W f, ".inst:hover{border-color:#a9c3cd}"
    W f, ".inst.sel{border-color:#16a7b4;background:#f1fafb}"
    W f, ".no{font-weight:700;color:#10222e;font-size:12px}.meta{font-size:10px;color:#7b8a9b;margin-top:2px}"
    W f, ".railNote{font-size:9px;color:#9aa8b6;margin:8px 2px 0}"
    W f, ".pcBtn{width:100%;border:1px dashed #9cc3cd;background:#f6fbfc;color:#0f8891;border-radius:10px;padding:11px;font-size:11px;font-weight:600;cursor:pointer;margin-top:4px}"
    W f, ".pcBtn:hover{background:#eaf7f8}"
    W f, ".card{background:#fff;border:1px solid #dfe6ed;border-radius:12px;box-shadow:0 4px 14px rgba(16,34,46,.06);padding:18px 18px 8px;margin-bottom:12px}"
    W f, ".secHead{position:relative;font-size:10px;font-weight:700;letter-spacing:2px;color:#0f8891;margin-bottom:12px}"
    W f, ".tag{position:absolute;right:52px;top:-1px;font-weight:600;color:#7b8a9b;letter-spacing:0}"
    W f, ".pager{position:absolute;right:0;top:-6px}"
    W f, ".pager a{display:inline-block;width:26px;height:26px;line-height:24px;text-align:center;border:1px solid #dfe6ed;border-radius:8px;color:#44586b;font-size:15px;margin-left:4px;cursor:pointer;background:#fbfcfe;text-decoration:none}"
    W f, ".pager a:hover{border-color:#16a7b4;color:#0f8891}"
    W f, ".field{display:inline-block;vertical-align:top;width:33%;padding-right:12px;margin-bottom:12px}"
    W f, ".label{font-size:10px;font-weight:600;color:#44586b;margin-bottom:5px}"
    W f, ".auto{font-size:8px;font-weight:700;color:#fff;background:#9aa8b6;border-radius:4px;padding:1px 4px;letter-spacing:1px}"
    W f, ".row{position:relative;padding-right:36px}"
    W f, "input[type=text]{box-sizing:border-box;width:100%;height:34px;border:1px solid #c9d5df;border-radius:8px;padding:6px 9px;font-size:13px;font-weight:600;color:#1d2d3c;background:#fbfcfe;font-family:'Segoe UI',Arial,sans-serif}"
    W f, "input[type=text]:focus{outline:none;border-color:#16a7b4;background:#fff}"
    W f, "input[type=text].ro{background:#eef2f6;color:#5d7185}"
    W f, ".unit{position:absolute;right:2px;top:2px;width:32px;height:30px;line-height:30px;text-align:center;font-size:9px;color:#7b8a9b;background:#e9eef3;border-radius:6px}"
    W f, ".hint{font-size:9px;color:#9aa8b6;margin-top:3px}"
    W f, ".boolRow{padding:6px 0 0}"
    W f, ".switch{position:relative;display:inline-block;width:40px;height:22px;vertical-align:middle;cursor:pointer}"
    W f, ".switch input{display:none}"
    W f, ".switch .knob{position:absolute;top:0;left:0;right:0;bottom:0;background:#c9d5df;border-radius:11px}"
    W f, ".switch .knob:before{content:'';position:absolute;left:3px;top:3px;width:16px;height:16px;background:#fff;border-radius:50%}"
    W f, ".switch input:checked + .knob{background:#16a7b4}"
    W f, ".switch input:checked + .knob:before{left:21px}"
    W f, ".toggleTxt{font-size:11px;font-weight:600;color:#44586b;margin-left:8px;vertical-align:middle}"
    W f, ".actions{text-align:right;padding:2px 0 4px}"
    W f, "button{border:1px solid #dfe6ed;border-radius:8px;padding:9px 14px;margin-left:6px;font-size:11px;font-weight:600;cursor:pointer;background:#fff;color:#44586b;font-family:'Segoe UI',Arial,sans-serif}"
    W f, "button:hover{border-color:#b9cbd6;background:#f6f9fb}"
    W f, "button.apply{background:#0f8891;border-color:#0f8891;color:#fff}"
    W f, "button.apply:hover{background:#0c7078}"
    W f, ".statusbar{padding:0 20px 6px;font-size:10px;color:#7b8a9b}"
    W f, ".statusbar .dot{width:7px;height:7px;margin-right:5px;background:#9aa8b6}"
    W f, ".statusbar .dot.busy{background:#f0b64b}.statusbar .dot.ok{background:#43c46b}.statusbar .dot.err{background:#e4574f}"
    W f, ".dirty{display:none;margin-left:10px;color:#c07a1f;font-weight:600}"
    W f, ".overlay{display:none;position:fixed;top:0;left:0;right:0;bottom:0;background:rgba(16,34,46,.45);z-index:50}"
    W f, ".modal{position:absolute;left:50%;top:42%;width:340px;margin-left:-170px;margin-top:-60px;background:#fff;border-radius:14px;padding:22px;box-shadow:0 18px 50px rgba(16,34,46,.35);text-align:center}"
    W f, ".modalTitle{font-size:15px;font-weight:700;color:#10222e}.modalBody{font-size:11px;color:#7b8a9b;margin:10px 0 16px}"
    W f, "input[type=text].bodySlot{font-size:11px}"
    W f, ".pickBtn{width:100%;border:1px dashed #9cc3cd;background:#f6fbfc;color:#0f8891;border-radius:8px;padding:7px;font-size:10px;font-weight:600;cursor:pointer;margin:5px 0 0}"
    W f, ".pickBtn:hover{background:#eaf7f8;border-color:#16a7b4}"
    W f, ".rmBox{border:1px solid #e1e8ee;background:#fbfcfe;border-radius:8px;padding:9px 10px;font-size:10px;color:#5d7185;min-height:40px;line-height:15px;word-wrap:break-word}"
    W f, ".rmBox.ok{background:#f2fbf4;border-color:#c9e9d0;color:#2e7d4f}"
    W f, ".rmBox.err{background:#fdf3f2;border-color:#efcfcc;color:#b03a30}"
    W f, ".rmActions{text-align:right;border-top:1px solid #eef2f6;padding:10px 0 8px}"
    W f, "button.rmOne{background:#c0392b;border-color:#c0392b}"
    W f, "button.rmOne:hover{background:#a93226;border-color:#a93226}"
    W f, "</style>"
End Sub


' ============================================================
' Dashboard v2 - JavaScript (IE9-safe)
' ============================================================
Sub WriteJs(f, cmd, rsp, count, bodyCopyName, bodyTargetName)
    On Error Resume Next
    W f, "<script language='javascript'>"
    W f, "var cp='" & JS(cmd) & "';var rp='" & JS(rsp) & "';var normal=false;var handoff=false;"
    W f, "var count=" & CStr(count) & ";var cur=1;var dirty=false;"
    W f, "var bd={};bd[1]={c:'" & JS(bodyCopyName) & "',t:'" & JS(bodyTargetName) & "'};"
    W f, "var binst=0;var bodyPick='';var rmInst=0;"
    W f, "function pickBody(which){bodyPick=which;var lab=(which=='COPY')?'Copy body (tool)':'Target body (to cut)';if(send('COMMAND=SELECTBODY\r\nWHICH='+which+'\r\nINSTANCE='+cur+'\r\n'))stat('Select the '+lab+' in CATIA - instance '+pad(cur)+'...','busy')}"
    W f, "function removeInstance(){if(!confirm('Subtract the copy body from the target body of instance '+pad(cur)+'?'))return;rmInst=cur;if(send('COMMAND=REMOVEONE\r\nINSTANCE='+cur+'\r\n')){setRmInfo('CATIA is pasting and removing...','');stat('Boolean Remove on instance '+pad(cur)+'...','busy')}}"
    W f, "function init(){var w=780,h=640;window.resizeTo(w,h);window.moveTo(screen.availWidth-w-18,18);buildList();document.getElementById('boolText').innerText=document.getElementById('externalFace').checked?'Yes':'No';setInterval(check,350)}"
    W f, "function $(i){return document.getElementById(i)}"
    W f, "function fs(){return new ActiveXObject('Scripting.FileSystemObject')}"
    W f, "function pad(n){return (n<10?'00':n<100?'0':'')+n}"
    W f, "function stat(t,c){$('statusText').innerText=t;$('statusDot').className='dot '+(c||'ok')}"
    W f, "function setBodySlots(i){var e=bd[i]||{c:'',t:''};binst=i;$('rmTag').innerText='Instance '+pad(i);$('bodyCopy').value=e.c||'Not selected';$('bodyTarget').value=e.t||'Not selected'}"
    W f, "function setRmInfo(t,c){$('rmInfo').innerText=t;$('rmInfo').className='rmBox'+(c?(' '+c):'')}"
    W f, "function setConn(b){$('connDot').className='dot'+(b?' busy':'');$('connText').innerText=b?'Processing':'Connected'}"
    W f, "function markDirty(){dirty=true;$('dirty').style.display='inline-block'}"
    W f, "function clearDirty(){dirty=false;$('dirty').style.display='none'}"
    W f, "function val(i){return document.getElementById(i).value.replace(',','.')}"
    W f, "function boolVal(){return document.getElementById('externalFace').checked?'true':'false'}"
    W f, "function syncBool(){document.getElementById('boolText').innerText=document.getElementById('externalFace').checked?'Yes':'No';markDirty()}"
    W f, "function send(t){try{var f=fs();if(f.FileExists(cp)){stat('CATIA is processing.');return false}var x=f.CreateTextFile(cp,true,false);x.Write(t);x.Close();setConn(true);return true}catch(e){stat(e.description||e,'err');return false}}"
    W f, "function buildList(){var i,html='';var wd=count;"
    W f, "if(count===0){html+='<div class=""inst""><div class=""no"">No complete instance</div><div class=""meta"">Run the fix-up macro</div></div>'}"
    W f, "for(i=1;i<=count;i++){html+='<div class=""inst'+(i===1?' sel':'')+'"" id=""inst'+i+'"" onclick=""selectInst('+i+')""><div class=""no"">PowerCopy Instance '+pad(i)+'</div><div class=""meta"" id=""meta'+i+'"">Loading...</div></div>'}"
    W f, "$('instList').innerHTML=html;$('railNote').innerText=count+' instance(s) detected';}"
    W f, "function selectInst(i){if(i<1||i>count)return;cur=i;var j,e;for(j=1;j<=count;j++){e=$('inst'+j);if(e)e.className='inst'+(j===cur?' sel':'')}$('secTag').innerText='Instance '+pad(cur);setBodySlots(cur);refreshData()}"
    W f, "function prevNext(d){selectInst(cur+d)}"
    W f, "function refreshData(){if(send('COMMAND=REFRESH\r\nINSTANCE='+cur+'\r\n'))stat('Reading instance '+pad(cur)+'...','busy')}"
    W f, "function applyData(){var t='COMMAND=UPDATE\r\nINSTANCE='+cur+'\r\n';"
    W f, "t=t+'" & p1 & "='+val('upper')+'\r\n';t=t+'" & p2 & "='+val('vertical')+'\r\n';"
    W f, "t=t+'" & P3 & "='+val('horizontal')+'\r\n';t=t+'" & P4 & "='+boolVal()+'\r\n';"
    W f, "t=t+'" & P5 & "='+val('headLength')+'\r\n';if(send(t))stat('Updating instance '+pad(cur)+'...','busy')}"
    W f, "function powerCopy(){if(send('COMMAND=POWERCOPY\r\n')){handoff=true;$('handoff').style.display='block'}}"
    W f, "function check(){try{var f=fs();if(!f.FileExists(rp))return;var x=f.OpenTextFile(rp,1);var t=x.ReadAll();x.Close();f.DeleteFile(rp,true);readRsp(t)}catch(e){}}"
    W f, "function readRsp(t){var o={};var a=t.split(/\r?\n/);for(var i=0;i<a.length;i++){var p=a[i].indexOf('=');if(p>0)o[a[i].substring(0,p)]=a[i].substring(p+1)}"
    W f, "if(o.BSTATUS){var bi=(o.BINST&&o.BINST!=='0')?parseInt(o.BINST,10):0;var cls='';"
    W f, "if(bi>0){if(!bd[bi])bd[bi]={c:'',t:''};if(bodyPick=='COPY')bd[bi].c=o.BCOPY||bd[bi].c;if(bodyPick=='TARGET')bd[bi].t=o.BTARGET||bd[bi].t;if(bi===cur)setBodySlots(cur)}"
    W f, "bodyPick='';"
    W f, "if(o.BSTATUS=='OK')cls='ok';"
    W f, "if(o.BSTATUS=='FAILED'||o.BSTATUS=='CANCELLED')cls='err';"
    W f, "setRmInfo(o.BMSG||'',cls);"
    W f, "if(o.BFEATURE)$('rmInfo').innerText=o.BFEATURE+'  -  '+(o.BMSG||'');"
    W f, "setConn(false);stat(o.BMSG||o.BSTATUS,(o.BSTATUS=='OK')?'ok':'err');"
    W f, "if(rmInst>0)refreshData();"
    W f, "rmInst=0;return}"
    W f, "if(o.STATUS=='OK'){"
    W f, "$('upper').value=o.V1;$('vertical').value=o.V2;$('horizontal').value=o.V3;"
    W f, "$('externalFace').checked=(o.V4=='true');$('headLength').value=o.V5;"
    W f, "$('stroke').value=o.V6;$('draft').value=(o.V7&&o.V7!='-')?o.V7:'-';"
    W f, "$('statStroke').innerText=o.V6;$('statDraft').innerText=(o.V7&&o.V7!='-')?o.V7:'-';"
    W f, "$('boolText').innerText=(o.V4=='true')?'Yes':'No';"
    W f, "$('meta'+cur).innerText=(o.V7&&o.V7!='-')?('Draft '+o.V7+' deg'):'No draft';"
    W f, "clearDirty();setConn(false);stat('Instance '+pad(cur)+' updated'+(o.DIAG?(' - '+o.DIAG):''))}"
    W f, "if(o.STATUS=='NOT_FOUND'){setConn(false);stat('Selected instance not found.','err')}"
    W f, "if(o.STATUS=='INCOMPLETE'){setConn(false);stat('Required parameter missing.','err')}}"
    W f, "function closeDash(){normal=true;send('COMMAND=CLOSE\r\n');window.close()}"
    W f, "function closeAfter(){normal=true;window.close()}"
    W f, "function closing(){if(!normal&&!handoff)send('COMMAND=CLOSE\r\n')}"
    W f, "document.onkeydown=function(e){e=e||window.event;"
    W f, "if(e.keyCode==13&&!handoff){var t=e.target||e.srcElement;"
    W f, "if(t&&t.tagName=='INPUT'&&t.type=='text'&&!t.readOnly)applyData()}}"
    W f, "</script>"
End Sub


'==================================================================
' VBScript runtime helpers
'------------------------------------------------------------------
' Replacements for the VBA intrinsics that VBScript does not have:
' Environ$, Format$, Shell, Sleep/DoEvents and the Open/Print #
' file statements.
'==================================================================

Function TempDir()
    On Error Resume Next
    Dim d
    d = gShell.ExpandEnvironmentStrings("%TEMP%")
    If Len(d) = 0 Or InStr(d, "%") > 0 Then d = gFso.GetSpecialFolder(2).Path
    If Right(d, 1) = "\" Then d = Left(d, Len(d) - 1)
    TempDir = d
    Err.Clear
End Function

Function Pad2(n)
    Pad2 = Right("0" & CStr(n), 2)
End Function

Function Pad3(n)
    Pad3 = Right("00" & CStr(n), 3)
End Function

'------------------------------------------------------------------
' Format$(Now, "yyyymmdd_hhnnss") / Format$(Now, "hhnnss")
'------------------------------------------------------------------
Function StampText(pattern)
    On Error Resume Next
    Dim d, timePart
    d = Now
    timePart = Pad2(Hour(d)) & Pad2(Minute(d)) & Pad2(Second(d))
    If InStr(1, pattern, "y", 1) > 0 Then
        StampText = CStr(Year(d)) & Pad2(Month(d)) & Pad2(Day(d)) & "_" & timePart
    Else
        StampText = timePart
    End If
    Err.Clear
End Function

'------------------------------------------------------------------
' Shell x, vbNormalFocus
'------------------------------------------------------------------
Sub ShellRun(commandLine)
    On Error Resume Next
    gShell.Run commandLine, 1, False
    Err.Clear
End Sub

'------------------------------------------------------------------
' Sleep without DoEvents: a blocking ping for the long waits (no CPU
' burn while the HTA dashboard is used), a Timer loop for short ones.
'------------------------------------------------------------------
'==================================================================
' Command server - driven by the PW-User application
'------------------------------------------------------------------
' IMPORTANT: VBScript has no DoEvents, so a waiting loop inside this
' script would freeze CATIA for as long as the dashboard is open.
' The application therefore owns the loop: it launches the HTA, polls
' the command file and calls RunCommand() once per user action. Each
' call returns immediately, so CATIA stays fully interactive.
'==================================================================

Dim gPart, gDoc

'------------------------------------------------------------------
' Human readable list of the parameters that could not be resolved,
' with the number of candidates found in the whole tree - so the
' message says WHAT is missing instead of "one of these two".
'------------------------------------------------------------------
Function MissingList(part, a, b, c, d, e)
    On Error Resume Next
    Dim missing
    missing = ""
    If a Is Nothing Then missing = AppendMissing(missing, part, p1)
    If b Is Nothing Then missing = AppendMissing(missing, part, p2)
    If c Is Nothing Then missing = AppendMissing(missing, part, P3)
    If d Is Nothing Then missing = AppendMissing(missing, part, P4)
    If e Is Nothing Then missing = AppendMissing(missing, part, P5)
    If Len(missing) > 0 Then
        MissingList = "These parameters were not found on instance: " & missing & _
                      vbCrLf & "Right-click the Parameters icon of the PW toolbar to dump the parameter tree."
    Else
        MissingList = ""
    End If
    Err.Clear
End Function

Function AppendMissing(current, part, wantedName)
    On Error Resume Next
    Dim all, text
    Set all = NewStore()
    CollectNamedParams part.Parameters.RootParameterSet, wantedName, all
    text = wantedName & " (" & CStr(all.Count) & " candidate(s) in the tree)"
    If Len(current) = 0 Then
        AppendMissing = text
    Else
        AppendMissing = current & ", " & text
    End If
    Err.Clear
End Function

'------------------------------------------------------------------
' Diagnostic dump: the whole parameter tree + what the dashboard
' detects, written next to the session files and opened by the app.
'------------------------------------------------------------------
Function DumpParameterTree()
    On Error Resume Next
    Dim doc, part, path, f, sets, i

    DumpParameterTree = "ERROR:no CATPart is active"
    If CATIA.Documents.Count = 0 Then Exit Function
    If TypeName(CATIA.ActiveDocument) <> "PartDocument" Then Exit Function

    Set doc = CATIA.ActiveDocument
    Set part = doc.Part
    Set gPart = part
    Set gDoc = doc

    path = SessionDir() & "\parameter-tree.txt"
    DeleteFile path
    Set f = NewWriter(path)
    If f Is Nothing Then
        DumpParameterTree = "ERROR:the report file could not be written"
        Exit Function
    End If

    f.WriteLine "PW-User - lifter parameter diagnostic"
    f.WriteLine "Document : " & doc.Name
    f.WriteLine "Generated: " & CStr(Now)
    f.WriteLine ""
    f.WriteLine "=========== PARAMETER TREE ==========="
    DumpSet f, part.Parameters.RootParameterSet, ""

    f.WriteLine ""
    f.WriteLine "=========== WHAT THE DASHBOARD DETECTS ==========="
    Set sets = GetUndercutSets(part)
    f.WriteLine "UNDERCUT sets (need " & p1 & " + " & p2 & " + " & P3 & " + " & P4 & "): " & CStr(sets.Count)
    For i = 1 To sets.Count
        f.WriteLine "   " & CStr(i) & ") " & CStr(sets.Item(i).Name)
    Next
    Set sets = GetHeadSets(part)
    f.WriteLine "LIFTER_HEAD sets (need " & P5 & "): " & CStr(sets.Count)
    For i = 1 To sets.Count
        f.WriteLine "   " & CStr(i) & ") " & CStr(sets.Item(i).Name)
    Next
    f.WriteLine "Instances shown by the dashboard: " & CStr(InstanceCount(part))

    f.WriteLine ""
    f.WriteLine "=========== RELATIONS ==========="
    DumpRelations f, part

    f.WriteLine ""
    f.WriteLine "=========== PARAMETER SEARCH ==========="
    DumpSearch f, part, p1
    DumpSearch f, part, p2
    DumpSearch f, part, P3
    DumpSearch f, part, P4
    DumpSearch f, part, P5
    DumpSearch f, part, P_STROKE
    DumpSearch f, part, P_DRAFT

    f.Close
    Err.Clear
    DumpParameterTree = "OK|" & path
End Function

Sub DumpSet(f, parentSet, indent)
    On Error Resume Next
    Dim direct, childSets, i, p, value

    f.WriteLine indent & "[SET] " & CStr(parentSet.Name)

    Set direct = Nothing
    Set direct = parentSet.DirectParameters
    Err.Clear
    If Not direct Is Nothing Then
        For i = 1 To direct.Count
            Set p = direct.Item(i)
            value = ""
            value = CStr(p.ValueAsString)
            Err.Clear
            f.WriteLine indent & "    - " & CStr(p.Name) & "  =  " & value & "   [" & TypeName(p) & "]"
        Next
    End If
    Err.Clear

    Set childSets = Nothing
    Set childSets = parentSet.ParameterSets
    Err.Clear
    If childSets Is Nothing Then Exit Sub
    For i = 1 To childSets.Count
        DumpSet f, childSets.Item(i), indent & "    "
    Next
    Err.Clear
End Sub

Sub DumpRelations(f, part)
    On Error Resume Next
    Dim relations, rel, i, leftName, state
    Set relations = Nothing
    Set relations = part.Relations
    Err.Clear
    If relations Is Nothing Then
        f.WriteLine "(no relation)"
        Exit Sub
    End If

    f.WriteLine "Relations: " & CStr(relations.Count)
    For i = 1 To relations.Count
        Set rel = Nothing
        Set rel = relations.Item(i)
        If Not rel Is Nothing Then
            leftName = ""
            leftName = CStr(rel.LeftPart.Name)
            Err.Clear
            state = ""
            If rel.Activity Then
                state = "active"
            Else
                state = "DEACTIVATED"
            End If
            Err.Clear
            f.WriteLine "   " & CStr(i) & ") " & CStr(rel.Name) & "  [" & TypeName(rel) & ", " & state & "]" & _
                        "  drives: " & leftName
        End If
    Next
    Err.Clear
End Sub

Sub DumpSearch(f, part, wantedName)
    On Error Resume Next
    Dim all, i
    Set all = NewStore()
    CollectNamedParams part.Parameters.RootParameterSet, wantedName, all
    f.WriteLine wantedName & " : " & CStr(all.Count) & " match(es)"
    For i = 1 To all.Count
        f.WriteLine "    " & CStr(i) & ") " & CStr(all.Item(i).Name) & "  =  " & CStr(all.Item(i).ValueAsString)
    Next
    Err.Clear
End Sub

'------------------------------------------------------------------
' Finds a parameter of one instance even when the CATPart stores it
' in another set than expected: the preferred set first, then the
' second set, then the whole parameter tree (nth match = nth
' instance). HAS_EXTERNAL_FACE, for example, lives in the UNDERCUT
' set on some templates and next to UNDERCUT_LENGTH on others.
'------------------------------------------------------------------
Function FindInstanceParam(part, primarySet, secondarySet, wantedName, instanceIndex)
    On Error Resume Next
    Dim p, all, pick
    Set FindInstanceParam = Nothing

    Set p = Nothing
    If Not primarySet Is Nothing Then Set p = FindDirect(primarySet, wantedName)
    If p Is Nothing And Not secondarySet Is Nothing Then Set p = FindDirect(secondarySet, wantedName)

    If p Is Nothing Then
        Set all = NewStore()
        CollectNamedParams part.Parameters.RootParameterSet, wantedName, all
        If all.Count > 0 Then
            pick = instanceIndex
            If pick < 1 Then pick = 1
            If pick > all.Count Then pick = all.Count
            Set p = all.Item(pick)
        End If
    End If

    Set FindInstanceParam = p
    Err.Clear
End Function

'------------------------------------------------------------------
' Every parameter of the tree whose leaf name matches, in tree order.
'------------------------------------------------------------------
Sub CollectNamedParams(parentSet, wantedName, result)
    On Error Resume Next
    Dim direct, childSets, child, i

    Set direct = Nothing
    Set direct = parentSet.DirectParameters
    Err.Clear
    If Not direct Is Nothing Then
        For i = 1 To direct.Count
            If StrComp(LeafName(CStr(direct.Item(i).Name)), wantedName, vbTextCompare) = 0 Then
                result.Add result.Count + 1, direct.Item(i)
            End If
        Next
    End If
    Err.Clear

    Set childSets = Nothing
    Set childSets = parentSet.ParameterSets
    Err.Clear
    If childSets Is Nothing Then Exit Sub
    For i = 1 To childSets.Count
        Set child = childSets.Item(i)
        CollectNamedParams child, wantedName, result
    Next
    Err.Clear
End Sub

Function SessionDir()
    On Error Resume Next
    Dim d
    d = TempDir() & "\PWLifterSession"
    If Not gFso.FolderExists(d) Then gFso.CreateFolder d
    SessionDir = d
    Err.Clear
End Function

Function CmdPath()
    CmdPath = SessionDir() & "\cmd.txt"
End Function

Function RspPath()
    RspPath = SessionDir() & "\rsp.txt"
End Function

Function DashboardPath()
    DashboardPath = SessionDir() & "\dashboard.hta"
End Function

Function StatePath()
    StatePath = SessionDir() & "\bodies.txt"
End Function

'------------------------------------------------------------------
' Step 1: prepare the session and BUILD the dashboard, then return.
'   NOSTROKE                       STROKE_Distance must be measured
'   OK|<hta>|<linked>|<drafts>     ready, the app launches the HTA
'   ERROR:<reason>
'------------------------------------------------------------------
Function PrepareSession()
    On Error Resume Next
    PrepareSession = "ERROR:The lifter dashboard could not be prepared."

    If CATIA.Documents.Count = 0 Then
        PrepareSession = "ERROR:No document is open in CATIA - open the CATPart first."
        Exit Function
    End If
    If TypeName(CATIA.ActiveDocument) <> "PartDocument" Then
        PrepareSession = "ERROR:The active CATIA document must be a CATPart."
        Exit Function
    End If

    Set gDoc = CATIA.ActiveDocument
    Set gPart = gDoc.Part
    If Err.Number <> 0 Then
        PrepareSession = "ERROR:The CATPart is not accessible."
        Exit Function
    End If

    If Not StrokeParameterExists(gPart) Then
        PrepareSession = "NOSTROKE"
        Exit Function
    End If

    Dim linked, drafts
    linked = LinkStrokeToMainBody(gPart)
    drafts = CreateDraftParameters(gPart)

    DeleteFile CmdPath()
    DeleteFile RspPath()
    DeleteFile DashboardPath()
    Err.Clear

    BuildDashboard DashboardPath(), CmdPath(), RspPath(), gDoc.Name, gPart, APP_TITLE, linked, drafts
    If Not gFso.FileExists(DashboardPath()) Then
        PrepareSession = "ERROR:The dashboard file could not be written."
        Exit Function
    End If

    PrepareSession = "OK|" & DashboardPath() & "|" & CStr(linked) & "|" & CStr(drafts)
    Err.Clear
End Function

'------------------------------------------------------------------
' Step 2: execute exactly ONE dashboard command and return at once.
' Returns the command name (REFRESH / UPDATE / SELECTBODY / REMOVEONE
' / POWERCOPY / CLOSE), "IDLE" when there is nothing to do, or
' "ERROR:<reason>".
'------------------------------------------------------------------
Function RunCommand()
    On Error Resume Next
    RunCommand = "IDLE"

    If Not gFso.FileExists(CmdPath()) Then Exit Function
    Dim data
    data = ReadAll(CmdPath())
    DeleteFile CmdPath()
    If Len(Trim(data)) = 0 Then Exit Function

    If CATIA.Documents.Count = 0 Then
        RunCommand = "ERROR:No document is open in CATIA."
        Exit Function
    End If
    If TypeName(CATIA.ActiveDocument) <> "PartDocument" Then
        RunCommand = "ERROR:The active CATIA document must be a CATPart."
        Exit Function
    End If

    Set gDoc = CATIA.ActiveDocument
    Set gPart = gDoc.Part
    LoadBodyState

    Dim action, instanceIndex
    action = UCase(ReadKey(data, "COMMAND"))
    instanceIndex = ReadInstance(data)
    DeleteFile RspPath()

    If action = "REFRESH" Then SendValues gPart, RspPath(), instanceIndex
    If action = "UPDATE" Then UpdateValues gPart, data, RspPath(), instanceIndex
    If action = "SELECTBODY" Then ChooseInstanceBody gPart, data, RspPath(), APP_TITLE
    If action = "REMOVEONE" Then RunBooleanRemove gPart, RspPath(), instanceIndex
    If action = "POWERCOPY" Then StartPowerCopy

    SaveBodyState
    Err.Clear
    RunCommand = action
End Function

'------------------------------------------------------------------
' Boolean Remove selections survive between two commands in a file.
'------------------------------------------------------------------
Sub LoadBodyState()
    On Error Resume Next
    EnsureBodyCollections
    gCopyBodyNames.RemoveAll
    gTargetBodyNames.RemoveAll
    gCopyBodyObjects.RemoveAll
    gTargetBodyObjects.RemoveAll
    If Not gFso.FileExists(StatePath()) Then Exit Sub

    Dim lines, i, parts, idx
    lines = Split(Replace(ReadAll(StatePath()), vbCrLf, vbLf), vbLf)
    For i = 0 To UBound(lines)
        parts = Split(lines(i), "|")
        If UBound(parts) >= 2 Then
            idx = CLng(parts(1))
            If UCase(parts(0)) = "COPY" Then
                SetStoredText gCopyBodyNames, idx, parts(2)
                SetStoredText gCopyBodyObjects, idx, parts(2)
            End If
            If UCase(parts(0)) = "TARGET" Then
                SetStoredText gTargetBodyNames, idx, parts(2)
                SetStoredText gTargetBodyObjects, idx, parts(2)
            End If
        End If
    Next
    Err.Clear
End Sub

Sub SaveBodyState()
    On Error Resume Next
    Dim f, keys, i
    Set f = NewWriter(StatePath())
    If f Is Nothing Then Exit Sub
    keys = gCopyBodyNames.Keys
    For i = 0 To UBound(keys)
        f.WriteLine "COPY|" & CStr(CLng(keys(i))) & "|" & gCopyBodyNames.Item(keys(i))
    Next
    keys = gTargetBodyNames.Keys
    For i = 0 To UBound(keys)
        f.WriteLine "TARGET|" & CStr(CLng(keys(i))) & "|" & gTargetBodyNames.Item(keys(i))
    Next
    f.Close
    Err.Clear
End Sub

Sub SleepMs(milliseconds)
    On Error Resume Next
    Dim started, elapsed, seconds
    If milliseconds >= 500 Then
        seconds = Int(milliseconds / 1000) + 1
        gShell.Run "%COMSPEC% /c ping -n " & CStr(seconds + 1) & " 127.0.0.1 > nul", 0, True
        Err.Clear
        Exit Sub
    End If
    started = Timer
    Do
        elapsed = Timer - started
        If elapsed < 0 Then elapsed = elapsed + 86400
        If elapsed * 1000 >= milliseconds Then Exit Do
    Loop
    Err.Clear
End Sub
